FME workspace RPUID (backup).fmw

Parameters:
- DestDataset_XLSXW2 = C:\Users\1272695837C\Desktop\RPUID_Report1.xlsx   # Destination Microsoft Excel File
- SourceDataset_GEODATABASE_FILE = P:\COA\COAU Branch\03 Linear Segmentation\00 - LS Support Contract\Contractor Submittals\1 - Round 1 Bases\Davis Monthan\5 DM Final Resubmittal dated 5 Jul 16\DavisMonthan_ULS_20160701.gdb   # Source Esri File Geodatabase

Readers:
- GEODATABASE_FILE_1: GEODATABASE_FILE from $(SourceDataset_GEODATABASE_FILE)

Writers:
- XLSXW2_1: XLSXW2 to $(DestDataset_XLSXW2)

wWaterTreatment_P (reader GEODATABASE_FILE_1)
    attributes: OBJECTID integer, wWaterTreatmentIDPK char(20), sdsID guid, sdsFeatureName char(80), sdsFeatureDescription char(255), sdsMetadataID char(80), latitude double, longitude double, MGRS char(20), elevation double, elevationUOM char(25), CATCODE char(6), condRatingAssessDate char(8), condRatingMethod char(20), condRatingValue char(15), controlType char(6), expectedServiceLife double, baseServiceLifeAdjustFactor char(5), calculatedServiceLife double, effluentDischargeDiameter double, effluentDischargeDiameterUOM char(25), envWtrQualPermitIDFK char(50), facilityID char(10), functionalArea char(25), GEOLOC char(15), hasCathodicProtection char(3), hasLead char(3), influentDiameter double, influentDiameterUOM char(25), installedDate char(8),
      isCritical char(3), lastPMDate char(8), lastRepairDate char(8), linearSegmentationGrouping char(100), maintainedBy char(10), MDI double, notes char(255), numberOfFailures smallint, operationalStatus char(20), permitCompliance char(3), permitedFlowRate double, permittedFlowRateUOM char(45), PMtype char(15), projectID char(50), realPropertyNetworkIdentifier char(4), realPropertyUniqueIdentifier char(18), SCADAControlID char(20), SCADAMonitorID char(20), segmentID char(30), UCIAssessmentDate integer, UDI double, uniformatIIComponent char(8), uniformatIISection char(8), uniformatIISystem char(8), utilityConditionIndex float, utilityNetworkType char(14), waterNetworkSubtype char(25), waterTreatmentType char(25), installationID char(16), installationName char(100),
      siteID char(36), majorCommand char(10), realPropertySiteUniqueID char(20), wacInnrCode char(10), dataSteward char(20), country char(5), owner char(10), createDate date, creator char(30), dataCollection char(20), dataSource char(100), editor char(20), dateEdited date, metaNotes char(255), mediaLink char(255), narrative char(255), eExteriorLightIDPK char(20), insulationThicknessUOM char(25), reservoirType char(10), tPumpIDPK char(20), temperatureUOM char(20), wellDiameterUOM char(25), lastLeakSurvey char(8), hasMeter char(3), elevationGrate double, oType char(16), serviceLineType char(20), lastPumpedDate char(8), eGuyWireIDPK char(20), eDynamicProtectiveDeviceIDPK char(20),
      typeOfGasFuel char(20), ductBankWidth double, impairedWaterBody char(3), connectionPoint char(20), scheduledMaintenance char(8), aflLightingCiruitSupported char(255), septicTankCapacityUOM char(20), eVoltageRegulatorIDPK char(20), pipeDiameter double, dykeWidthUOM char(25), dOpenDrainageIDPK char(20), tMeterIDPK char(20), eUGPrimaryIDPK char(20), fuseSize char(30), elevationDischargePipe double, measuredLengthUOM char(25), weirLength double, commUtilityNodeIDPK char(20), isBonded char(3), dLineGravityIDPK char(20), isolationValvePitCount smallint, groundingType char(12), projectTitle char(100), wellFieldIDPK char(20), yearManufactured char(8), dControlValveIDPK char(20), oHydrantIDPK char(20), insulationCondition char(15), annualAverageDailyFlowUOM char(45), boxCulvertDimensionUOM char(25),
      turbineHeightUOM char(25), tRegulatorIDPK char(20), dimLengthUOM char(25), eSurfaceStructureIDPK char(20), expansionJointType char(23), elevationInvertInThree double, gFittingIDPK char(20), pipeNumber smallint, tankFooterHeightUOM char(25), gDripIDPK char(20), elevationTo double, annualHeatInput float, overalArchDimensionUOM char(25), fittingConnectionType char(15), hydrantNumber smallint, systemPurpose char(30), voltage char(15), transformerID char(40), oLineDefuelingIDPK char(20), solarArrayIDPK char(20), gRegulatorIDPK char(20), flowRangeMax double, strategicReserve char(3), sPumpIDPK char(20), invertDownstreamElevation double, pipeCasingIDPK char(20), coolingMethod char(18), manufacturerName char(100), pressureSettingUOM char(35), lowPointDrainCount smallint,
      zeroSequenceResistance double, fixtureHeight double, ductBankWidthUOM char(25), pumpType char(15), dynamicProtectiveDeviceType char(23), wellResource char(11), floorElevationUOM char(25), gOdorizerIDPK char(20), dCulvertIDPK char(20), accessDiameter double, tapChangerSetting double, specificMaterialType char(40), hasTieSwitch char(3), totalCapacity double, ductDiameterUOM char(25), averageDischarge double, securityCondition char(15), panelAngleDegrees double, capacityJet double, hydrantClass char(15), fittingWidth double, eOHPrimaryLineType char(11), setPressureStandard double, eOHTransmissionIDPK char(20), sampleLocationType char(30), pressureOperatingUOM char(35), surfaceStructureType char(25), elevationDischargePipeUOM char(25), electricalConditionRating char(15), isIsolation char(3),
      isAboveground char(3), oPumpIDPK char(20), percentTapAmount double, eUGSecondaryLineType char(11), hasFuse char(3), hasCableSupports char(3), treatmentLevel char(9), hasCurrentTransformer char(3), operatingPressureUOM char(35), gPigLaunchIDPK char(20), zeroSequenceReactance double, lensType char(15), gMeterIDPK char(20), tHeatCoolServiceIDPK char(20), elevationWeir double, switchID char(20), typeOfChemicalEnergy char(10), groundSurfaceElevation double, electricEnergyProducedUOM char(25), insulationThickness double, regulatorSizeUOM char(25), capacityJetUOM char(20), interruptingMedium char(7), useTypeSub char(30), controllableFittingType char(9), numOfFeeders smallint, eSwitchStationIDPK char(20), mountHeightUOM char(25), hasFireproofing char(3), pipeInstallation char(15),
      tHeatCoolMainIDPK char(20), faaRegistered char(3), mountingType char(20), inventoryControlNumber char(50), volume double, counterpoiseDiameter double, nozzleNumber smallint, inOutflowDiameter2 double, wLineServiceIDPK char(20), crossSectionShape char(13), designPressureEntered double, buryType char(15), oPumpStationIDPK char(20), septicTankCapacity double, septicTankType char(20), insulationLevel char(5), positiveSequenceResistance double, fireFlow double, voltagePrimary char(15), loadCapacity char(10), numberTanks double, pipeCount smallint, infiltration char(15), useType char(25), windingType char(8), maxContinuousCurrent double, insulationCoverDiameter double, generatorType char(6), riserMaterial char(40), dStorageReservoirIDPK char(20),
      dInletCoverType char(16), wasteWaterType char(15), eMeterIDPK char(20), tExpansionJointIDPK char(20), lampCount double, photocellType char(13), anodeCount smallint, tAnchorDPK char(20), bondJunctionType char(30), totalDepth double, capacityUOM char(20), totalDynamicHeadUOM char(25), drainType char(22), otherEquipment char(3), obstructionLight char(3), buriedDepth double, substationID char(50), lightStyle char(15), testPointType char(15), tPumpStationIDPK char(20), rimElevationUOM char(25), sMeterIDPK char(20), slopeUOM char(20), diameter double, meterMAOP double, eOHSecondaryIDPK char(20), elevationManholeTop double, landUseIDPK char(20), inputOutputPipeSizeUOM char(25), lightColor char(25),
      bypassSwitchIndicator char(3), depthElevation double, totalCapacityUOM char(25), turbineHeight double, hasSecContainment char(3), boreholeIDPK char(20), commNodeType char(20), rectifierVoltage char(15), pipeSchedule char(5), meterRating char(15), dInletIDPK char(20), typeOfSolidFuel char(20), lampType char(20), dischargePipeDiameterUOM char(25), pressureDownstream double, ratedPressure double, purposeOfSystem char(15), maxReactiveGeneration double, interruptingMechanism char(12), chemicalEnergyIDPK char(20), oControlValveType char(35), boreholeDiameterUOM char(25), remoteRead char(3), fillDate char(8), ductDiameter double, structuralCondition char(15), accessDiameterUOM char(25), tJunctionIDPK char(20), pressureSetting double, hasLoadTapChangerIndicator char(3),
      hasTemperatureGauge char(3), pipeCoating char(30), averageDailyRunTime smallint, peakDischarge double, statusOfSystem char(35), wControlValveIDPK char(20), SCADA char(3), deliveryPurchase char(3), lineCapacityUOM char(45), tControlValveType char(35), horizontalAccuracy double, oilWaterSepType char(8), dykeWidth double, ownerOperator char(30), annualElecGenUOM char(25), isVertical char(3), gasFittingType char(26), annualElecGen double, wellDiameter double, electricEnergyConsumedUOM char(25), RepairDate char(8), typeOfGeothermal char(20), latitudeFrom double, thermalFittingType char(7), tankTopHeightUOM char(25), elevationInvertOut double, elevationInvertOutUOM char(25), infiltrationSource char(37), samplingType char(30), wLineMainIDPK char(20),
      designPressureUOM char(35), cableCount integer, temperatureNorm double, manuallyOperatedIndicator char(3), valvePitDepthLength char(25), maxInterruptingCurrent double, ductBankHeight double, gasType char(15), eSubstationIDPK char(20), structureMaterial char(40), tripCount smallint, crossSectionAreaUOM char(20), dInetType char(24), windTurbineIDPK char(20), annualMaximumDailyFlow double, cathodicProtectionPointType char(20), maxPermittedFlowRateUOM char(45), locationType char(20), capacityOil double, failureDate char(8), hasSplice char(3), systemTechnology char(10), buckPercent char(7), isLined char(3), shieldingIndicator char(3), referencePointElevation double, flow double, operationNutConditionRating char(15), designCapacityUOM char(20), waterHydrantType char(30),
      sPumpStationIDPK char(20), nominalVoltage char(3), oOilWaterSepIDPK char(20), oTankFarmIDPK char(20), inputPipeSize double, treatmentRate double, measuredLength double, hasFaultIndicator char(3), hasSecondartyProtectiveDeivce char(3), dateCollected integer, isOperable char(3), heatCoolLineType char(29), tCondensateCollectorIDPK char(20), inOutFlowConnectionType1 char(30), ratedFlow double, sOilWaterSepIDPK char(20), numberValves double, tankOverflowHeight double, emerIsoloationSysStatus char(20), eStructureSupportIDPK char(20), erosionControlFeature char(30), wellFieldType char(5), inConduitIndicator char(3), leveeStation char(20), inletDiameterUOM char(25), leakDetection char(3), gPumpStationIDPK char(20), manufacturer char(25), springRange double, referencePointDescription char(100),
      polePier char(3), receivingWaterBody char(150), ventIndicator char(3), numberCondesatePumps smallint, fittinglWidthUOM char(25), depthElevationUOM char(25), flowRangeMin double, ratedPressureUOM char(35), wPumpIDPK char(20), workOrderNum char(25), staticPressure double, lengthSizeUOM char(25), isLocked char(3), oProductType char(16), wHydrantIDPK char(18), directionFacing char(10), grantName char(30), flowEquation char(20), peakLoad double, hydrantValveDiameter double, conductorSize char(10), elevationInvertInTwo double, mountHeight double, timeControlIndicator char(3), pressureRangeMax double, percentImpedance double, ratedkVA double, shuntMechanism char(20), obstructionLights char(3), elevationOrificeOutflowUOM char(25),
      elevationWeirUOM char(25), wPumpStationIDPK char(20), wMeterIDPK char(20), rimElevation double, gasUsageRate char(45), designCapacity double, cathodicProtectionLineType char(20), openDrainageType char(16), areaSizeUOM char(20), preferredCircuitSource char(20), capacityCFH double, ratedTertiaryKVA double, tControlValveIDPK char(20), sLinePressurizedMainIDPK char(20), poleCount smallint, poleNumber char(20), hasLightningArrestor char(3), gangOperatedIndicator char(3), backfillMaterial char(8), oAirEliminatorIDPK char(20), inOutFlowConnectionType2 char(30), gasUsage double, dDischargeIDPK char(20), sLinePressurizedServiceIDPK char(20), averageDischargeUOM char(45), rightOfWayWidth double, gLineDistributionIDPK char(20), heightUOM char(25), annualHeatInputUOM char(45), numberPipes double,
      containmentPipeMaterial char(40), annualAverageDailyFlow double, dykeCondition char(15), anodeMaterial char(30), fixtureType char(25), weirType char(25), impellerDiameter double, thermalPowerStationIDPK char(20), industryStandards char(3), orificeDiameter double, recevingBody char(50), sControlValveIDPK char(20), hasAirReliefValve char(3), linePressurizedType char(10), hasAltitudeValve char(3), mountType char(20), gPressureMonitoringDeviceIDPK char(20), sOutfallIDPK char(20), flowRangeUOM char(45), sFittingIDPK char(20), resevorCapacityUOM char(20), elevationInvertInThreeUOM char(25), material char(30), externalSurfaceConditionRating char(15), insulationValue char(10), gControlValveType char(35), powerRating double, pipeRoughness double, tankBottomHeightUOM char(25), owsContents char(20),
      StorageTankProductType char(20), phaseOrientation char(5), radiationHazardType char(20), numberOfTurbines integer, leachFieldCondition char(15), eOHPrimaryIDPK char(20), subtransientReactance double, exteriorLightRole char(23), boreholeType char(5), elevationInvertInOne double, gallonsOfFill double, isGrounded char(3), pressureOperating double, eSwitchIDPK char(20), transformerType char(12), hasPrefabricatedIndicator char(3), mountingConfiguration char(17), wellPurpose char(10), meterType char(26), PTRatio char(25), repairStatus char(25), isWinterized char(3), normalPosition char(10), powerFactor double, classification char(30), groundResistance double, elevationGrateUOM char(25), anodeWeight double, perimeterSize double, lengthOfBladeUOM char(25),
      numberOfPumps smallint, numOfTransformers smallint, inOutFlowConnectionType char(30), tankOverflowHeightUOM char(25), invertElevationUOM char(25), oFittingIDPK char(20), isPhotocellType char(3), hydrantType char(17), tFittingIDPK char(20), impellerNumber smallint, meterUse char(12), eAccessPointIDPK char(20), hasDykes char(3), counterpoiseDiameterUOM char(25), gScrubberIDPK char(20), resupplyCapacity double, lightningProtection char(3), peakDischargeUOM char(45), hydrantValveDiameterUOM char(25), pipeDiameterUOM char(25), pipeWallThickness char(5), cathodicProtectionIDPK char(20), anodeWeightUOM char(30), testPointWireCount char(8), pipeType char(12), pumpDesignHead char(30), controlValveType char(35), voltageClass char(15), Shape_Area double, inoutflowDiameterUOM char(25),
      weirMaterial char(40), inServiceDate integer, oMeterIDPK char(20), boringMethod char(16), remoteReadType char(25), pressureRating double, isMechanicalJoint char(3), storageTankFarmIDPK char(20), sSepticTankIDPK char(20), capacityLube double, boostPercent char(7), secondaryConfiguration char(10), einsulationType char(6), hasGuyWire char(3), utilityFailureIDPK char(20), fuseRating char(5), hasLiquidLevelIndicator char(3), ovalArchDimension char(5), gControlValveIDPK char(20), dischargeDiameterUOM char(25), insulationCoverMaterial char(15), solarPanelIDPK char(20), isRadial char(3), floorElevation double, exteriorLightType char(20), accessPointType char(11), sLineGravityServiceIDPK char(20), hydroelectricPowerIDPK char(20), poleClass char(255), commUtilitySegmentIDPK char(20),
      generalMaterialType char(40), oHydrantValve char(35), casingThickness double, electricEnergyProduced double, conductorConfiguration char(10), tJunctionType char(8), erosionControlIDPK char(20), casingThicknessUOM char(25), regulatorCapacity double, meterID char(15), typeOfSolarPanel char(37), endConnectionType char(11), gLineHeaterIDPK char(20), buriedDepthUOM char(25), gStrainerIDPK char(20), skimmer char(3), secondaryVoltage integer, isCoated char(3), dischargePipeMaterial char(40), culvertType char(37), commSegmentType char(20), longitudeTo double, dPumpIDPK char(20), motorized char(3), typeOfReactor char(28), capacityGas double, sLineGravityMainIDPK char(20), maxDifferentialPressure double, inDiameter double, storageCapacity char(7),
      outDiameter double, inletDiameter double, tankType char(20), fittinglLengthUOM char(25), inoutflowDiameter double, dischargeDiameter double, maxNominalVoltage char(3), isFused char(3), windFarmIDPK char(20), waterSourceType char(25), elevationInvertInOneUOM char(25), eConductorType char(13), MGRScentroid char(20), hasStaticGuard char(3), pressureRatedUOM char(35), invertElevation double, storageTankIDPK char(20), setPressureEntered double, drillingCompDate char(40), ePresentPosition char(7), annualMaximumDailyFlowUOM char(45), elevationManholeTopUOM char(25), dManholeIDPK char(20), Shape_Length double, amperage smallint, sControlValveType char(35), pressureRated double, isEncased char(3), dControlValveType char(35), capacityLubeUOM char(20),
      contractDate integer, tankFooterHeight double, insulationCoverDiameterUOM char(25), invertUpstreamElevation double, hasGritChamber char(3), rectifierCableGauge char(10), associatedLineType char(29), permittedFlowRate double, wMainLineType char(25), diameterUOM char(25), fittingType char(20), distressRatingType char(27), pressureRangeMin double, compartmentNumber char(20), ratedFlowUOM char(45), impellerDiameterUOM char(25), perimeterSizeUOM char(25), capacityOilUOM char(20), oFilterStrainerIDPK char(20), wattage double, hasGangOperatedIndicator char(3), inOutflowDiameter1 double, switchConfiguration char(8), tankTopHeight double, designPressureStandard double, electricalCondition char(15), thermalAnchorType char(11), isInsulated char(3), guyType char(255), hasCableGuard char(3),
      sCleanOutDPK char(20), wellIDPK char(20), elevationManholeInvertUOM char(25), fittingLength double, projectRECOwner char(40), height double, oControlValveIDPK char(20), slope double, oPigLaunchIDPK char(20), wFittingIDPK char(20), setPressureUOM char(35), samplingFrequency char(20), voltageRating char(15), rightOfWayWidthUOM char(25), capacityGasUOM char(20), hasRiser char(3), eCurrentRegulatorIDPK char(20), weirLengthUOM char(25), pressureRatingUOM char(35), landStatus char(9), gGasLampIDPK char(20), currentRegulatorType char(27), conductorMaterial char(15), oilCapacityUOM char(20), eCounterpoiseSystemIDPK char(20), outputPipeSize double, neutralType char(8), elevationFrom double, capacity double, electricPower char(20),
      regulationType char(20), fixtureHeightUOM char(25), elevationOrificeOutflow double, presentPosition char(10), pressureDownstreamUOM char(35), guySpanMaterial char(5), eGeneratorIDPK char(20), resevoirCapacity double, ratedKVARise double, longitudeFrom double, wFireHydrantIDPK char(18), hasSharedInsulatCoverIndicator char(3), gLineServiceIDPK char(20), eOHSecondaryLineType char(11), sensorIndicator char(3), structureSupportID char(30), BILRating char(5), pipeTestDate char(8), conductorType char(13), tankBottomHeight double, bodyOfWater char(50), pumpDesignHeadUOM char(25), pressureRangeUOM char(35), hasTieSwitchIndicator char(3), ductBankConfiguration char(50), electricalOutput double, sManholeIDPK char(20), leakRepairMethod char(10), maxPermitedFlowRate double, deadmanControlType char(3),
      hasKillSwitch char(3), eUGPrimaryLineType char(11), condensatePumpPower double, emagRadiationHazardIDPK char(20), zeroSequenceResistanceRatio double, eTransformerIDPK char(20), electricEnergyConsumed double, valvePitDepth double, hasInternalMeterIndicator char(3), oilVolumeUOM char(20), sTreatmentPlantIDPK char(20), timeControlStatus char(3), totalConduitLength double, polType char(16), lengthRiser double, startDate char(40), wasCompleted char(3), rectifierType char(20), boxCulvertDimension char(20), orificePipeMaterial char(40), encasementType char(8), hasByPassIndicator char(3), hasBypassValve char(3), totalDynamicHead char(25), typeOfThermalSolar char(20), oInstallationPipelineIDPK char(20), elevationManholeInvert double, closingResistor double, fillType char(11), crossSectionArea double,
      enclosureCondition char(15), sampleIDPK char(20), numberOfDucts double, elevationInvertInTwoUOM char(25), photocellStatus char(3), highWaterElevation char(20), gAlcoholInjectionEquipmentIDPK char(20), projectNumber char(12), regulatorSize double, phaseType char(11), hydrantClearance char(3), orificeDiameterUOM char(25), primaryFuseType char(9), isGated char(3), verticalAccuracy double, treatmentType char(24), structureType char(25), isLooped char(3), sampleDevice char(30), depthHeightUOM char(25), operatingPressure double, spareConduitNumber smallint, temperatureMax double, reliefCapacityUOM char(45), switchType char(25), contractType char(40), areaSize double, planDurationInYears double, boreholeDiameter double, wetWallCapacity double,
      dikeType char(30), lineCapacity double, serialNumber char(100), serviceIndicator char(3), weightUOM char(30), highPointVentCount smallint, meterMAOPUOM char(35), depthHeight double, eUGTransmissionIDPK char(20), eUGSecondaryIDPK char(20), ductBankHeightUOM char(25), typeOfLiquidFuel char(21), terminationType char(10), primaryVoltage char(3), isSampled char(3), fcSegmentID integer, effluentDischarge char(8), electricalOutputUOM char(25), model char(100), tRegulatorType char(21), oilCapacity double, totalConduitLengthUOM char(25), dischargePipeDiameter double, calibration char(8), bedMaterial char(16), wSourceIDPK char(20), numberOfNeutrals smallint, oInterterminalPipelineIDPK char(20), transientReactance double, sGreaseTrapIDPK char(20),
      tinsulationType char(26), volumeUOM char(20), pipeLining char(20), lengthOfBlade double, numberOfTaps smallint, hasCondensatePump char(3), structuralConditionRating char(15), treatmentProcess char(28), lengthSize double, eConduitSystemIDPK char(20), dimension char(20), drainageLineType char(10), latitudeTo double
    -> BulkAttributeRenamer
BulkAttributeRenamer
    PATTERN_ACTION_DISP = CASECHANGE
    CASE_CHANGE_TYPE = lower
    MODE_CHOICE = RENAME
    ATTRCHOICE = All Attributes
    -> AttributeFilter
AttributeFilter
    ATTR_VALUES = <EMPTY>,<MISSING>,<NULL>,<UNFILTERED>,TBD,NA,77777,99999
    ATTR_NAME = realpropertyuniqueidentifier
    <UNFILTERED> -> AttributeCreator
AttributeCreator
    ATTR_TABLE:
      SET_TO FileName = @Value(fme_basename)
      SET_TO Feature = @Value(fme_feature_type)
    -> DuplicateRemover
DuplicateRemover: DuplicateFilter
    INPUT_ORDERED_CHOICE = No
    KEYATTR = fme_feature_type fme_basename utilitynetworktype installationid siteid realpropertyuniqueidentifier catcode
    UNIQUE -> RPUID_Output (writer XLSXW2_1)
RPUID_Output (writer XLSXW2_1)
    attributes: FileName string(100,format_type;Simple;font_type;;font_color;;fill_color;;custom_options;;text_wrap;no), Feature string(14,format_type;Simple;font_type;;font_color;;fill_color;;custom_options;;text_wrap;no), installationid string(16,format_type;Simple;font_type;;font_color;;fill_color;;custom_options;;text_wrap;no), siteid string(36,format_type;Simple;font_type;;font_color;;fill_color;;custom_options;;text_wrap;no), realpropertyuniqueidentifier string(18,format_type;Simple;font_type;;font_color;;fill_color;;custom_options;;text_wrap;no), catcode string(6,format_type;Simple;font_type;;font_color;;fill_color;;custom_options;;text_wrap;no), utilitynetworktype string(14,format_type;Simple;font_type;;font_color;;fill_color;;custom_options;;text_wrap;no)
