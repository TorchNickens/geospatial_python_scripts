FME workspace linePointDiameterCompare - Copy.fmw

Parameters:
- SourceDataset_FILEGDB = P:\COA\COAU Branch\03 Linear Segmentation\00 - LS Support Contract\Contractor Submittals\Nellis\Final Submittal 20170719\ULS_Nellis_20170719.gdb   # Source Geodatabase
- DestDataset_XLSXW = P:\COA\COAU Branch\03 Linear Segmentation\00 - LS Support Contract\Contractor Submittals\Nellis\Final Submittal 20170719\GIS Review\Nellis_Diameter_Compare.xlsx   # Destination Microsoft Excel File

Readers:
- FILEGDB_1: FILEGDB from $(SourceDataset_FILEGDB)

Writers:
- XLSXW_1: XLSXW to $(DestDataset_XLSXW)

utilitiesThermal/tHeatCoolMain_L (reader FILEGDB_1)
    attributes: OBJECTID objectid, tHeatCoolMainIDPK text(20), sdsID guid, sdsFeatureName text(80), sdsFeatureDescription text(255), sdsMetadataID text(80), lengthSize double, lengthSizeUOM text(184), latitudeFrom double, latitudeTo double, longitudeFrom double, longitudeTo double, elevationFrom double, elevationTo double, elevationUOM text(184), CATCODE text(6), condRatingAssessDate text(8), condRatingMethod text(87), condRatingValue text(120), expectedServiceLife double, baseServiceLifeAdjustFactor text(76), calculatedServiceLife double, depthHeight double, depthHeightUOM text(184), facilityID text(10), functionalArea text(35), generalMaterialType text(8), specificMaterialType text(76), GEOLOC text(15), hasCathodicProtection text(77),
      hasPrefabricatedIndicator text(77), hasSharedInsulatCoverIndicator text(77), heatCoolLineType text(76), installedDate text(8), insulationCoverDiameter text(76), insulationCoverDiameterUOM text(184), insulationCoverMaterial text(76), insulationThickness double, insulationThicknessUOM text(184), insulationValue text(10), inventoryControlNumber text(50), isVertical text(77), lastPMDate text(8), lastRepairDate text(8), linearSegmentationGrouping text(100), maintainedBy text(76), MDI double, notes text(255), numberOfFailures smallint, operatingPressure double, operatingPressureUOM text(136), operationalStatus text(76), pipeDiameter text(76), pipeDiameterUOM text(184), pipeInstallation text(76), pipeRoughness double, pipeTestDate text(8), PMtype text(76), projectID text(50), ratedPressure double,
      ratedPressureUOM text(136), realPropertyNetworkIdentifier text(4), realPropertyUniqueIdentifier text(18), segmentID text(30), temperatureMax double, temperatureNorm double, temperatureUOM text(159), tinsulationType text(76), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date, creator text(30), dataCollection text(255), dataSource text(100), editor text(20), dateEdited date,
      metaNotes text(255), mediaLink text(255), narrative text(255), Shape_Length double
    -> Tester_48
Tester_48
    TEST_CLAUSE:
      TEST @Value(operationalStatus) = removed
      TEST @Value(operationalStatus) = abandoned
    TEST_MODE = Automatic
    BOOL_OP = OR
    TEST_DESCRIPTION = ""
    FAILED -> Owner_33
Owner_33: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_14
AttributeKeeper_14
    KEEP_ATTRS = OBJECTID,pipeDiameter,fme_feature_type
    -> PointOnLineOverlayer_9 [LINE]
utilitiesThermal/tHeatCoolService_L (reader FILEGDB_1)
    attributes: OBJECTID objectid, tHeatCoolServiceIDPK text(20), sdsID guid, sdsFeatureName text(80), sdsFeatureDescription text(255), sdsMetadataID text(80), lengthSize double, lengthSizeUOM text(184), latitudeFrom double, latitudeTo double, longitudeFrom double, longitudeTo double, elevationFrom double, elevationTo double, elevationUOM text(184), CATCODE text(6), condRatingAssessDate text(8), condRatingMethod text(87), condRatingValue text(120), expectedServiceLife double, baseServiceLifeAdjustFactor text(76), calculatedServiceLife double, depthHeight double, depthHeightUOM text(184), facilityID text(10), functionalArea text(35), generalMaterialType text(8), specificMaterialType text(76), GEOLOC text(15), hasCathodicProtection text(77),
      hasPrefabricatedIndicator text(77), hasSharedInsulatCoverIndicator text(77), heatCoolLineType text(76), installedDate text(8), insulationCoverDiameter text(76), insulationCoverDiameterUOM text(184), insulationCoverMaterial text(76), insulationThickness double, insulationThicknessUOM text(184), insulationValue text(10), inventoryControlNumber text(50), isVertical text(77), lastPMDate text(8), lastRepairDate text(8), linearSegmentationGrouping text(100), maintainedBy text(76), MDI double, notes text(255), numberOfFailures smallint, operatingPressure double, operatingPressureUOM text(136), operationalStatus text(76), pipeDiameter text(76), pipeDiameterUOM text(184), pipeInstallation text(76), pipeRoughness double, pipeTestDate text(8), PMtype text(76), projectID text(50), ratedPressure double,
      ratedPressureUOM text(136), realPropertyNetworkIdentifier text(4), realPropertyUniqueIdentifier text(18), segmentID text(30), temperatureMax double, temperatureNorm double, temperatureUOM text(159), tinsulationType text(76), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date, creator text(30), dataCollection text(255), dataSource text(100), editor text(20), dateEdited date,
      metaNotes text(255), mediaLink text(255), narrative text(255), Shape_Length double
    -> Tester_49
Tester_49
    TEST_CLAUSE:
      TEST @Value(operationalStatus) = removed
      TEST @Value(operationalStatus) = abandoned
    TEST_MODE = Automatic
    BOOL_OP = OR
    TEST_DESCRIPTION = ""
    FAILED -> Owner_34
Owner_34: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_13
AttributeKeeper_13
    KEEP_ATTRS = OBJECTID,fme_feature_type,pipeDiameter
    -> PointOnLineOverlayer_10 [LINE]
utilitiesThermal/tRegulator_P (reader FILEGDB_1)
    attributes: OBJECTID objectid, tRegulatorIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), expectedServiceLife double, baseServiceLifeAdjustFactor text(76), calculatedServiceLife double, depthHeight double, depthHeightUOM text(184), facilityID text(10), functionalArea text(35), GEOLOC text(15), hasCathodicProtection text(77), installedDate text(8), inventoryControlNumber text(50), lastPMDate text(8), lastRepairDate text(8), linearSegmentationGrouping text(100),
      maintainedBy text(76), manufacturerName text(100), MDI double, model text(50), notes text(255), numberOfFailures smallint, operationalStatus text(76), PMtype text(76), projectID text(50), realPropertyNetworkIdentifier text(4), realPropertyUniqueIdentifier text(18), regulatorSize double, regulatorSizeUOM text(184), segmentID text(30), setPressureEntered double, setPressureStandard double, setPressureUOM text(136), springRange double, tRegulatorType text(76), UCIAssessmentDate int, UDI double, uniformatIIComponent text(49), uniformatIISection text(61), uniformatIISystem text(39), utilityConditionIndex single, utilityNetworkType text(133), installationID text(76), installationName text(76), siteID text(78), majorCommand text(76),
      realPropertySiteUniqueID text(80), wacInnrCode text(10), dataSteward text(20), country text(76), owner text(76), createDate date, creator text(30), dataCollection text(255), dataSource text(100), editor text(20), dateEdited date, metaNotes text(255), mediaLink text(255), narrative text(255)
    -> Tester_50
utilitiesThermal/tPumpStation_P (reader FILEGDB_1)
    attributes: OBJECTID objectid, tPumpStationIDPK text(20), sdsID guid, sdsFeatureName text(80), sdsFeatureDescription text(255), sdsMetadataID text(80), latitude double, longitude double, MGRS text(20), elevation double, elevationUOM text(184), annualAverageDailyFlow double, annualAverageDailyFlowUOM text(76), annualMaximumDailyFlow double, annualMaximumDailyFlowUOM text(76), CATCODE text(6), condRatingAssessDate text(8), condRatingMethod text(87), condRatingValue text(120), expectedServiceLife double, baseServiceLifeAdjustFactor text(76), calculatedServiceLife double, designCapacity double, designCapacityUOM text(187), envWtrQualPermitIDFK text(50), facilityID text(10), functionalArea text(35), GEOLOC text(15), hasCathodicProtection text(77), highWaterElevation text(20),
      installedDate text(8), inventoryControlNumber text(50), lastPMDate text(8), lastRepairDate text(8), linearSegmentationGrouping text(100), maintainedBy text(76), manufacturerName text(100), MDI double, notes text(255), numberOfFailures smallint, numberOfPumps smallint, operationalStatus text(76), permitCompliance text(77), permittedFlowRate double, permittedFlowRateUOM text(76), PMtype text(76), projectID text(50), realPropertyNetworkIdentifier text(4), realPropertyUniqueIdentifier text(18), SCADAControlID text(20), SCADAMonitorID text(20), segmentID text(30), UCIAssessmentDate int, UDI double, uniformatIIComponent text(49), uniformatIISection text(61), uniformatIISystem text(39), utilityConditionIndex single, utilityNetworkType text(133), wetWallCapacity double,
      installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_50
utilitiesThermal/tExpansionJoint_P (reader FILEGDB_1)
    attributes: OBJECTID objectid, tExpansionJointIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), expectedServiceLife double, baseServiceLifeAdjustFactor text(76), calculatedServiceLife double, depthHeight double, depthHeightUOM text(184), diameter text(76), diameterUOM text(184), expansionJointType text(76), functionalArea text(35), GEOLOC text(18), hasCathodicProtection text(77), inServiceDate text(8), installedDate text(8), inventoryControlNumber text(50), lastPMDate text(8),
      lastRepairDate text(8), linearSegmentationGrouping text(100), maintainedBy text(76), manufacturerName text(100), MDI double, model text(50), notes text(255), numberOfFailures smallint, operationalStatus text(76), PMtype text(76), projectID text(50), ratedPressure double, ratedPressureUOM text(136), realPropertyNetworkIdentifier text(4), realPropertyUniqueIdentifier text(18), segmentID text(30), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20),
      country text(76), owner text(76), createDate date, creator text(30), dataCollection text(255), dataSource text(100), editor text(20), dateEdited date, metaNotes text(255), mediaLink text(255), narrative text(255)
    -> Tester_50
utilitiesThermal/tPumpStation_A (reader FILEGDB_1)
    attributes: OBJECTID objectid, tPumpStationIDPK text(20), sdsID guid, sdsFeatureName text(80), sdsFeatureDescription text(255), sdsMetadataID text(80), areaSize double, areaSizeUOM text(139), perimeterSize double, perimeterSizeUOM text(184), latitude double, longitude double, MGRScentroid text(20), annualAverageDailyFlow double, annualAverageDailyFlowUOM text(76), annualMaximumDailyFlow double, annualMaximumDailyFlowUOM text(76), CATCODE text(6), condRatingAssessDate text(8), condRatingMethod text(87), condRatingValue text(120), expectedServiceLife double, baseServiceLifeAdjustFactor text(76), calculatedServiceLife double, designCapacity double, designCapacityUOM text(187), envWtrQualPermitIDFK text(50), facilityID text(10), functionalArea text(35), GEOLOC text(15),
      hasCathodicProtection text(77), highWaterElevation text(20), installedDate text(8), inventoryControlNumber text(50), lastPMDate text(8), lastRepairDate text(8), linearSegmentationGrouping text(100), maintainedBy text(76), manufacturerName text(100), MDI double, notes text(255), numberOfFailures smallint, numberOfPumps smallint, operationalStatus text(76), permitCompliance text(77), permittedFlowRate double, permittedFlowRateUOM text(76), PMtype text(76), projectID text(50), realPropertyNetworkIdentifier text(4), realPropertyUniqueIdentifier text(18), SCADAControlID text(20), SCADAMonitorID text(20), segmentID text(30), UCIAssessmentDate int, UDI double, uniformatIIComponent text(49), uniformatIISection text(61), uniformatIISystem text(39), utilityConditionIndex single,
      utilityNetworkType text(133), wetWallCapacity double, installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255), Shape_Length double, Shape_Area double
    -> Tester_50
utilitiesThermal/tAnchor_P (reader FILEGDB_1)
    attributes: OBJECTID objectid, tAnchorDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), expectedServiceLife double, baseServiceLifeAdjustFactor text(76), calculatedServiceLife double, depthHeight double, depthHeightUOM text(184), facilityID text(10), functionalArea text(35), GEOLOC text(15), hasCathodicProtection text(77), installedDate text(8), inventoryControlNumber text(50), isWinterized text(77), lastPMDate text(8), lastRepairDate text(8), linearSegmentationGrouping text(100),
      maintainedBy text(76), manufacturerName text(100), MDI double, model text(50), notes text(255), numberOfFailures smallint, operationalStatus text(76), PMtype text(76), projectID text(50), realPropertyNetworkIdentifier text(4), realPropertyUniqueIdentifier text(18), segmentID text(30), thermalAnchorType text(76), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date,
      creator text(30), dataCollection text(255), dataSource text(100), editor text(20), dateEdited date, metaNotes text(255), mediaLink text(255), narrative text(255)
    -> Tester_50
utilitiesThermal/tCondensateCollector_P (reader FILEGDB_1)
    attributes: OBJECTID objectid, tCondensateCollectorIDPK text(20), sdsID guid, sdsFeatureName text(80), sdsFeatureDescription text(255), sdsMetadataID text(80), latitude double, longitude double, MGRS text(20), elevation double, elevationUOM text(184), associatedLineType text(76), capacity double, capacityUOM text(187), CATCODE text(6), condensatePumpPower double, condRatingAssessDate text(8), condRatingMethod text(87), condRatingValue text(120), expectedServiceLife double, baseServiceLifeAdjustFactor text(76), calculatedServiceLife double, depthHeight double, depthHeightUOM text(184), diameter text(76), diameterUOM text(184), facilityID text(10), functionalArea text(35), generalMaterialType text(8), specificMaterialType text(76),
      GEOLOC text(15), hasCathodicProtection text(77), hasCondensatePump text(77), inputOutputPipeSizeUOM text(184), inputPipeSize double, installedDate text(8), inventoryControlNumber text(50), lastPMDate text(8), lastRepairDate text(8), linearSegmentationGrouping text(100), maintainedBy text(76), manufacturerName text(100), MDI double, model text(50), notes text(255), numberCondesatePumps smallint, numberOfFailures smallint, operationalStatus text(76), outputPipeSize double, PMtype text(76), projectID text(50), realPropertyNetworkIdentifier text(4), realPropertyUniqueIdentifier text(18), segmentID text(30), UCIAssessmentDate int, UDI double, uniformatIIComponent text(49), uniformatIISection text(61), uniformatIISystem text(39), utilityConditionIndex single,
      utilityNetworkType text(133), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_50
utilitiesThermal/tMeter_P (reader FILEGDB_1)
    attributes: OBJECTID objectid, tMeterIDPK text(20), sdsID guid, sdsFeatureName text(80), sdsFeatureDescription text(255), sdsMetadataID text(80), latitude double, longitude double, MGRS text(20), elevation double, elevationUOM text(184), calibration text(8), CATCODE text(6), condRatingAssessDate text(8), condRatingMethod text(87), condRatingValue text(120), controlType text(76), expectedServiceLife double, baseServiceLifeAdjustFactor text(76), calculatedServiceLife double, depthHeight double, depthHeightUOM text(184), facilityID text(10), flowRangeMax double, flowRangeMin double, flowRangeUOM text(76), functionalArea text(35), GEOLOC text(15), hasByPassIndicator text(77), hasCathodicProtection text(77),
      installedDate text(8), inventoryControlNumber text(50), lastPMDate text(8), lastRepairDate text(8), linearSegmentationGrouping text(100), maintainedBy text(76), manufacturerName text(100), MDI double, meterMAOP double, meterMAOPUOM text(136), meterType text(255), model text(50), notes text(255), numberOfFailures smallint, operationalStatus text(76), pipeNumber smallint, PMtype text(76), pressureRangeMax double, pressureRangeMin double, pressureRangeUOM text(136), projectID text(50), ratedFlow double, ratedFlowUOM text(76), realPropertyNetworkIdentifier text(8), realPropertyUniqueIdentifier text(18), remoteRead text(77), remoteReadType text(76), segmentID text(30), UCIAssessmentDate int, UDI double,
      uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_50
utilitiesThermal/tPump_P (reader FILEGDB_1)
    attributes: OBJECTID objectid, tPumpIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), expectedServiceLife double, baseServiceLifeAdjustFactor text(76), calculatedServiceLife double, depthHeight double, depthHeightUOM text(184), diameter text(76), diameterUOM text(184), facilityID text(10), functionalArea text(35), GEOLOC text(15), hasCathodicProtection text(77), impellerDiameter text(76), impellerDiameterUOM text(184), installedDate text(8),
      inventoryControlNumber text(50), lastPMDate text(8), lastRepairDate text(8), linearSegmentationGrouping text(100), maintainedBy text(76), manufacturerName text(100), MDI double, model text(50), notes text(255), numberOfFailures smallint, operationalStatus text(76), PMtype text(76), projectID text(50), ratedFlow double, ratedFlowUOM text(76), realPropertyNetworkIdentifier text(4), realPropertyUniqueIdentifier text(18), SCADAControlID text(20), SCADAMonitorID text(20), segmentID text(30), totalDynamicHead text(25), UCIAssessmentDate int, UDI double, uniformatIIComponent text(49), uniformatIISection text(61), uniformatIISystem text(39), utilityConditionIndex single, utilityNetworkType text(133), installationID text(76), installationName text(76),
      siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_50
utilitiesThermal/tControlValve_P (reader FILEGDB_1)
    attributes: OBJECTID objectid, tControlValveIDPK text(20), sdsID guid, sdsFeatureName text(80), sdsFeatureDescription text(255), sdsMetadataID text(80), latitude double, longitude double, MGRS text(20), elevation double, elevationUOM text(184), associatedLineType text(76), CATCODE text(6), condRatingAssessDate text(8), condRatingMethod text(87), condRatingValue text(120), controlType text(76), expectedServiceLife double, baseServiceLifeAdjustFactor text(76), calculatedServiceLife double, depthHeight double, depthHeightUOM text(184), diameter text(76), diameterUOM text(184), facilityID text(10), functionalArea text(35), GEOLOC text(15), hasBypassValve text(77), hasCathodicProtection text(77), installedDate text(8),
      inventoryControlNumber text(50), isOperable text(77), lastPMDate text(8), lastRepairDate text(8), linearSegmentationGrouping text(100), maintainedBy text(76), manufacturerName text(100), MDI double, model text(50), notes text(255), numberOfFailures smallint, operationalStatus text(76), PMtype text(76), projectID text(50), realPropertyNetworkIdentifier text(4), realPropertyUniqueIdentifier text(18), segmentID text(30), setPressureEntered double, setPressureStandard double, setPressureUOM text(136), tControlValveType text(255), UCIAssessmentDate int, UDI double, uniformatIIComponent text(49), uniformatIISection text(61), uniformatIISystem text(39), utilityConditionIndex single, utilityNetworkType text(133), installationID text(76), installationName text(76),
      siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_50
utilitiesThermal/tJunction_P (reader FILEGDB_1)
    attributes: OBJECTID objectid, tJunctionIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), expectedServiceLife double, baseServiceLifeAdjustFactor text(76), calculatedServiceLife double, depthHeight double, depthHeightUOM text(184), drainType text(76), facilityID text(10), functionalArea text(35), GEOLOC text(15), hasAirReliefValve text(77), hasCathodicProtection text(77), installedDate text(8), inventoryControlNumber text(50), lastPMDate text(8), lastRepairDate text(8),
      linearSegmentationGrouping text(100), maintainedBy text(76), manufacturerName text(100), MDI double, model text(50), notes text(255), numberOfFailures smallint, numberPipes double, numberValves double, operationalStatus text(76), PMtype text(76), projectID text(50), realPropertyNetworkIdentifier text(4), realPropertyUniqueIdentifier text(18), segmentID text(30), tJunctionType text(76), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20),
      country text(76), owner text(76), createDate date, creator text(30), dataCollection text(255), dataSource text(100), editor text(20), dateEdited date, metaNotes text(255), mediaLink text(255), narrative text(255)
    -> Tester_50
utilitiesThermal/tFitting_P (reader FILEGDB_1)
    attributes: OBJECTID objectid, tFittingIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), expectedServiceLife double, baseServiceLifeAdjustFactor text(76), calculatedServiceLife double, depthHeight double, depthHeightUOM text(184), diameter text(76), diameterUOM text(184), facilityID text(10), functionalArea text(35), GEOLOC text(15), hasCathodicProtection text(77), installedDate text(8), inventoryControlNumber text(50), lastPMDate text(8),
      lastRepairDate text(8), linearSegmentationGrouping text(100), maintainedBy text(76), manufacturerName text(100), MDI double, model text(50), notes text(255), numberOfFailures smallint, operationalStatus text(76), pipeCount smallint, PMtype text(76), projectID text(50), realPropertyNetworkIdentifier text(4), realPropertyUniqueIdentifier text(18), segmentID text(30), thermalFittingType text(76), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20),
      country text(76), owner text(76), createDate date, creator text(30), dataCollection text(255), dataSource text(100), editor text(20), dateEdited date, metaNotes text(255), mediaLink text(255), narrative text(255)
    -> Tester_50
Tester_50
    TEST_CLAUSE:
      TEST @Value(operationalStatus) = removed
      TEST @Value(operationalStatus) = abandoned
    TEST_MODE = Automatic
    BOOL_OP = OR
    TEST_DESCRIPTION = ""
    FAILED -> Owner_35
Owner_35: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_12
AttributeKeeper_12
    KEEP_ATTRS = OBJECTID,diameter,fme_feature_type
    -> PointOnLineOverlayer_9 [POINT]
    -> PointOnLineOverlayer_10 [POINT]
PointOnLineOverlayer_9
    TOLERANCE = .00000001
    ATTR_ACCUM_MODE = Merge Incoming
    OV_ATTR = _overlaps
    ATTR_CONFLICT_RES = Use Original
    POINT -> Tester_12
Tester_12
    TEST_CLAUSE:
      TEST pipeDiameter ATTRIBUTE_VALUE_NULL ""
      TEST pipeDiameter ATTRIBUTE_IS_EMPTY ""
      TEST pipeDiameter ATTRIBUTE_IS_MISSING ""
      TEST @Value(pipeDiameter) = @Value(diameter)
    TEST_MODE = Automatic
    BOOL_OP = OR
    TEST_DESCRIPTION = ""
    FAILED -> AttributeCreator_12
AttributeCreator_12
    ATTR_TABLE = SET_TO Feature = @Value(fme_feature_type)
    -> tHeatCoolMain_L (writer XLSXW_1)
tHeatCoolMain_L (writer XLSXW_1)
    attributes: Feature auto(20), OBJECTID number(20), diameter auto(20), pipeDiameter auto(20)
PointOnLineOverlayer_10
    TOLERANCE = .00000001
    ATTR_ACCUM_MODE = Merge Incoming
    OV_ATTR = _overlaps
    ATTR_CONFLICT_RES = Use Original
    POINT -> Tester_4
Tester_4
    TEST_CLAUSE:
      TEST pipeDiameter ATTRIBUTE_VALUE_NULL ""
      TEST pipeDiameter ATTRIBUTE_IS_EMPTY ""
      TEST pipeDiameter ATTRIBUTE_IS_MISSING ""
      TEST @Value(pipeDiameter) = @Value(diameter)
    TEST_MODE = Automatic
    BOOL_OP = OR
    TEST_DESCRIPTION = ""
    FAILED -> AttributeCreator_4
AttributeCreator_4
    ATTR_TABLE = SET_TO Feature = @Value(fme_feature_type)
    -> tHeatCoolService_L (writer XLSXW_1)
tHeatCoolService_L (writer XLSXW_1)
    attributes: Feature auto(20), OBJECTID number(20), diameter auto(20), pipeDiameter auto(20)
utilitiesFuels/oInstallationPipeline_L (reader FILEGDB_1)
    attributes: OBJECTID objectid, oInstallationPipelineIDPK text(20), sdsID guid, sdsFeatureName text(80), sdsFeatureDescription text(255), sdsMetadataID text(80), lengthSize double, lengthSizeUOM text(184), latitudeFrom double, latitudeTo double, longitudeFrom double, longitudeTo double, elevationFrom double, elevationTo double, elevationUOM text(184), CATCODE text(6), condRatingAssessDate text(8), condRatingMethod text(87), condRatingValue text(120), containmentPipeMaterial text(76), expectedServiceLife double, baseServiceLifeAdjustFactor text(76), calculatedServiceLife double, depthHeight double, depthHeightUOM text(184), facilityID text(10), functionalArea text(35), generalMaterialType text(8), specificMaterialType text(76), GEOLOC text(15),
      hasCathodicProtection text(77), highPointVentCount smallint, installedDate text(8), insulationCondition text(120), inventoryControlNumber text(50), isCoated text(77), isLined text(77), isolationValvePitCount smallint, lastPMDate text(8), lastRepairDate text(8), leakDetection text(77), linearSegmentationGrouping text(100), lowPointDrainCount smallint, maintainedBy text(76), MDI double, notes text(255), numberOfFailures smallint, operationalStatus text(76), pipeDiameter text(76), pipeDiameterUOM text(184), pipeInstallation text(76), pipeWallThickness text(30), PMtype text(76), polType text(76), pressureRating double, pressureRatingUOM text(136), projectID text(50), ratedFlow double, ratedFlowUOM text(76), realPropertyNetworkIdentifier text(4),
      realPropertyUniqueIdentifier text(18), segmentID text(30), UCIAssessmentDate int, UDI double, uniformatIIComponent text(49), uniformatIISection text(61), uniformatIISystem text(39), utilityConditionIndex single, utilityNetworkType text(133), valvePitDepth double, valvePitDepthLength text(184), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255), Shape_Length double
    -> Tester_51
Tester_51
    TEST_CLAUSE:
      TEST @Value(operationalStatus) = removed
      TEST @Value(operationalStatus) = abandoned
    TEST_MODE = Automatic
    BOOL_OP = OR
    TEST_DESCRIPTION = ""
    FAILED -> Owner_36
Owner_36: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_17
AttributeKeeper_17
    KEEP_ATTRS = OBJECTID,pipeDiameter,fme_feature_type
    -> PointOnLineOverlayer_11 [LINE]
utilitiesFuels/oLineDefueling_L (reader FILEGDB_1)
    attributes: OBJECTID objectid, oLineDefuelingIDPK text(20), sdsID guid, sdsFeatureName text(80), sdsFeatureDescription text(255), sdsMetadataID text(80), lengthSize double, lengthSizeUOM text(184), latitudeFrom double, latitudeTo double, longitudeFrom double, longitudeTo double, elevationFrom double, elevationTo double, elevationUOM text(184), CATCODE text(6), condRatingAssessDate text(8), condRatingMethod text(87), condRatingValue text(120), expectedServiceLife double, baseServiceLifeAdjustFactor text(76), calculatedServiceLife double, depthHeight double, depthHeightUOM text(184), facilityID text(10), functionalArea text(35), generalMaterialType text(8), specificMaterialType text(76), GEOLOC text(15), hasCathodicProtection text(77),
      installedDate text(8), insulationCondition text(120), inventoryControlNumber text(50), isCoated text(77), isLined text(77), lastPMDate text(8), lastRepairDate text(8), leakDetection text(77), linearSegmentationGrouping text(100), maintainedBy text(76), MDI double, notes text(255), numberOfFailures smallint, operationalStatus text(76), oType text(76), pipeDiameter text(76), pipeDiameterUOM text(184), pipeInstallation text(76), PMtype text(76), pressureRating double, pressureRatingUOM text(136), projectID text(50), ratedFlow double, ratedFlowUOM text(76), realPropertyNetworkIdentifier text(4), realPropertyUniqueIdentifier text(18), segmentID text(30), UCIAssessmentDate int, UDI double, uniformatIIComponent text(49),
      uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255), Shape_Length double
    -> Tester_52
Tester_52
    TEST_CLAUSE:
      TEST @Value(operationalStatus) = removed
      TEST @Value(operationalStatus) = abandoned
    TEST_MODE = Automatic
    BOOL_OP = OR
    TEST_DESCRIPTION = ""
    FAILED -> Owner_37
Owner_37: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_16
AttributeKeeper_16
    KEEP_ATTRS = OBJECTID,fme_feature_type,pipeDiameter
    -> PointOnLineOverlayer_12 [LINE]
utilitiesFuels/oInterterminalPipeline_L (reader FILEGDB_1)
    attributes: OBJECTID objectid, oInterterminalPipelineIDPK text(20), sdsID guid, sdsFeatureName text(80), sdsFeatureDescription text(255), sdsMetadataID text(80), lengthSize double, lengthSizeUOM text(184), latitudeFrom double, latitudeTo double, longitudeFrom double, longitudeTo double, elevationFrom double, elevationTo double, elevationUOM text(184), CATCODE text(6), condRatingAssessDate text(8), condRatingMethod text(87), condRatingValue text(120), expectedServiceLife double, baseServiceLifeAdjustFactor text(76), calculatedServiceLife double, depthHeight double, depthHeightUOM text(184), facilityID text(10), functionalArea text(35), generalMaterialType text(8), specificMaterialType text(76), GEOLOC text(15), hasCathodicProtection text(77),
      installedDate text(8), insulationCondition text(120), inventoryControlNumber text(50), isCoated text(77), isLined text(77), lastPMDate text(8), lastRepairDate text(8), leakDetection text(77), linearSegmentationGrouping text(100), maintainedBy text(76), MDI double, notes text(255), numberOfFailures smallint, operationalStatus text(76), oType text(76), pipeDiameter text(76), pipeDiameterUOM text(184), pipeInstallation text(76), PMtype text(76), pressureRating double, pressureRatingUOM text(136), projectID text(50), ratedFlow double, ratedFlowUOM text(76), realPropertyNetworkIdentifier text(4), realPropertyUniqueIdentifier text(18), rightOfWayWidth double, rightOfWayWidthUOM text(184), segmentID text(30), UCIAssessmentDate int,
      UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255), Shape_Length double
    -> Tester_53
Tester_53
    TEST_CLAUSE:
      TEST @Value(operationalStatus) = removed
      TEST @Value(operationalStatus) = abandoned
    TEST_MODE = Automatic
    BOOL_OP = OR
    TEST_DESCRIPTION = ""
    FAILED -> Owner_38
Owner_38: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_18
AttributeKeeper_18
    KEEP_ATTRS = OBJECTID,fme_feature_type,pipeDiameter
    -> PointOnLineOverlayer_13 [LINE]
utilitiesFuels/oFilterStrainer_P (reader FILEGDB_1)
    attributes: OBJECTID objectid, oFilterStrainerIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), expectedServiceLife double, baseServiceLifeAdjustFactor text(76), calculatedServiceLife double, depthHeight double, depthHeightUOM text(184), functionalArea text(35), GEOLOC text(15), hasCathodicProtection text(77), installedDate text(8), inventoryControlNumber text(50), lastPMDate text(8), lastRepairDate text(8), linearSegmentationGrouping text(100), maintainedBy text(76), manufacturerName text(100),
      MDI double, model text(50), notes text(255), numberOfFailures smallint, operationalStatus text(76), PMtype text(76), projectID text(50), realPropertyNetworkIdentifier text(4), realPropertyUniqueIdentifier text(18), segmentID text(30), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date, creator text(30), dataCollection text(255), dataSource text(100),
      editor text(20), dateEdited date, metaNotes text(255), mediaLink text(255), narrative text(255)
    -> Tester_54
utilitiesFuels/oPump_P (reader FILEGDB_1)
    attributes: OBJECTID objectid, oPumpIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), expectedServiceLife double, coolingMethod text(76), baseServiceLifeAdjustFactor text(76), calculatedServiceLife double, depthHeight double, depthHeightUOM text(184), dischargeDiameter text(76), dischargeDiameterUOM text(184), facilityID text(10), functionalArea text(35), GEOLOC text(15), hasCathodicProtection text(77), impellerNumber smallint, inletDiameter text(76),
      inletDiameterUOM text(184), installedDate text(8), inventoryControlNumber text(50), lastPMDate text(8), lastRepairDate text(8), leakDetection text(77), linearSegmentationGrouping text(100), maintainedBy text(76), manufacturerName text(100), MDI double, model text(50), notes text(255), numberOfFailures smallint, operationalStatus text(76), pipeCount smallint, PMtype text(76), projectID text(50), ratedFlow double, ratedFlowUOM text(76), ratedPressure double, ratedPressureUOM text(76), realPropertyNetworkIdentifier text(4), realPropertyUniqueIdentifier text(18), SCADAControlID text(20), SCADAMonitorID text(20), segmentID text(30), serialNumber text(100), totalDynamicHead text(25), totalDynamicHeadUOM text(76), UCIAssessmentDate int,
      UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_54
utilitiesFuels/oPigLaunch_P (reader FILEGDB_1)
    attributes: OBJECTID objectid, oPigLaunchIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), expectedServiceLife double, baseServiceLifeAdjustFactor text(76), calculatedServiceLife double, diameter text(76), diameterUOM text(184), functionalArea text(35), GEOLOC text(15), hasCathodicProtection text(77), installedDate text(8), inventoryControlNumber text(50), lastPMDate text(8), lastRepairDate text(8), linearSegmentationGrouping text(100), maintainedBy text(76), MDI double,
      model text(50), notes text(255), numberOfFailures smallint, operationalStatus text(76), PMtype text(76), projectID text(50), realPropertyNetworkIdentifier text(4), realPropertyUniqueIdentifier text(18), segmentID text(30), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date, creator text(30), dataCollection text(255), dataSource text(100), editor text(20),
      dateEdited date, metaNotes text(255), mediaLink text(255), narrative text(255)
    -> Tester_54
utilitiesFuels/oControlValve_P (reader FILEGDB_1)
    attributes: OBJECTID objectid, oControlValveIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), expectedServiceLife double, baseServiceLifeAdjustFactor text(76), calculatedServiceLife double, depthHeight double, depthHeightUOM text(184), diameter text(76), diameterUOM text(184), facilityID text(10), functionalArea text(35), GEOLOC text(15), hasBypassValve text(77), hasCathodicProtection text(77), installedDate text(8), inventoryControlNumber text(50),
      lastPMDate text(8), lastRepairDate text(8), leakDetection text(77), linearSegmentationGrouping text(100), maintainedBy text(76), manufacturerName text(100), MDI double, model text(50), notes text(255), numberOfFailures smallint, oControlValveType text(255), operationalStatus text(76), pipeCount smallint, PMtype text(76), projectID text(50), realPropertyNetworkIdentifier text(4), realPropertyUniqueIdentifier text(18), segmentID text(30), UCIAssessmentDate int, UDI double, uniformatIIComponent text(49), uniformatIISection text(61), uniformatIISystem text(39), utilityConditionIndex single, utilityNetworkType text(133), installationID text(76), installationName text(76), siteID text(78), majorCommand text(76), realPropertySiteUniqueID text(80),
      wacInnrCode text(10), dataSteward text(20), country text(76), owner text(76), createDate date, creator text(30), dataCollection text(255), dataSource text(100), editor text(20), dateEdited date, metaNotes text(255), mediaLink text(255), narrative text(255)
    -> Tester_54
utilitiesFuels/oOilWaterSep_P (reader FILEGDB_1)
    attributes: OBJECTID objectid, oOilWaterSepIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), expectedServiceLife double, baseServiceLifeAdjustFactor text(76), calculatedServiceLife double, depthHeight double, depthHeightUOM text(184), envWtrQualPermitIDFK text(50), facilityID text(10), functionalArea text(35), GEOLOC text(15), hasCathodicProtection text(77), hasGritChamber text(77), installedDate text(8), inventoryControlNumber text(50), lastPMDate text(8), lastRepairDate text(8),
      linearSegmentationGrouping text(100), maintainedBy text(76), manufacturerName text(100), MDI double, model text(50), notes text(255), numberOfFailures smallint, oilCapacity double, oilCapacityUOM text(187), operationalStatus text(76), owsContents text(20), permitCompliance text(77), pipeCount smallint, PMtype text(76), projectID text(50), ratedFlow double, ratedFlowUOM text(76), realPropertyNetworkIdentifier text(4), realPropertyUniqueIdentifier text(18), segmentID text(30), UCIAssessmentDate int, UDI double, uniformatIIComponent text(49), uniformatIISection text(61), uniformatIISystem text(39), utilityConditionIndex single, utilityNetworkType text(133), volume double, volumeUOM text(187), installationID text(76),
      installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_54
Tester_54
    TEST_CLAUSE:
      TEST @Value(operationalStatus) = removed
      TEST @Value(operationalStatus) = abandoned
    TEST_MODE = Automatic
    BOOL_OP = OR
    TEST_DESCRIPTION = ""
    FAILED -> Owner_39
Owner_39: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_15
AttributeKeeper_15
    KEEP_ATTRS = OBJECTID,dischargeDiameter,hydrantValveDiameter,inletDiameter,diameter,fme_feature_type
    -> PointOnLineOverlayer_13 [POINT]
    -> PointOnLineOverlayer_12 [POINT]
    -> PointOnLineOverlayer_11 [POINT]
PointOnLineOverlayer_11
    TOLERANCE = .00000001
    ATTR_ACCUM_MODE = Merge Incoming
    OV_ATTR = _overlaps
    ATTR_CONFLICT_RES = Use Original
    POINT -> Tester_14
Tester_14
    TEST_CLAUSE:
      TEST pipeDiameter ATTRIBUTE_VALUE_NULL ""
      TEST pipeDiameter ATTRIBUTE_IS_EMPTY ""
      TEST pipeDiameter ATTRIBUTE_IS_MISSING ""
      TEST @Value(pipeDiameter) = @Value(diameter)
      TEST @Value(pipeDiameter) = @Value(dischargeDiameter)
      TEST @Value(pipeDiameter) = @Value(inletDiameter)
    TEST_MODE = Automatic
    BOOL_OP = OR
    TEST_DESCRIPTION = ""
    FAILED -> AttributeCreator_15
AttributeCreator_15
    ATTR_TABLE = SET_TO Feature = @Value(fme_feature_type)
    -> oInstallationPipeline_L (writer XLSXW_1)
oInstallationPipeline_L (writer XLSXW_1)
    attributes: Feature auto(20), OBJECTID number(20), diameter auto(20), pipeDiameter auto(20)
PointOnLineOverlayer_12
    TOLERANCE = .00000001
    ATTR_ACCUM_MODE = Merge Incoming
    OV_ATTR = _overlaps
    ATTR_CONFLICT_RES = Use Original
    POINT -> Tester_13
Tester_13
    TEST_CLAUSE:
      TEST pipeDiameter ATTRIBUTE_VALUE_NULL ""
      TEST pipeDiameter ATTRIBUTE_IS_EMPTY ""
      TEST pipeDiameter ATTRIBUTE_IS_MISSING ""
      TEST @Value(pipeDiameter) = @Value(diameter)
      TEST @Value(pipeDiameter) = @Value(dischargeDiameter)
      TEST @Value(pipeDiameter) = @Value(inletDiameter)
    TEST_MODE = Automatic
    BOOL_OP = OR
    TEST_DESCRIPTION = ""
    FAILED -> AttributeCreator_14
AttributeCreator_14
    ATTR_TABLE = SET_TO Feature = @Value(fme_feature_type)
    -> oLineDefueling_L (writer XLSXW_1)
oLineDefueling_L (writer XLSXW_1)
    attributes: Feature auto(20), OBJECTID number(20), diameter auto(20), pipeDiameter auto(20)
PointOnLineOverlayer_13
    TOLERANCE = .00000001
    ATTR_ACCUM_MODE = Merge Incoming
    OV_ATTR = _overlaps
    ATTR_CONFLICT_RES = Use Original
    POINT -> Tester_5
Tester_5
    TEST_CLAUSE:
      TEST pipeDiameter ATTRIBUTE_VALUE_NULL ""
      TEST pipeDiameter ATTRIBUTE_IS_EMPTY ""
      TEST pipeDiameter ATTRIBUTE_IS_MISSING ""
      TEST @Value(pipeDiameter) = @Value(diameter)
      TEST @Value(pipeDiameter) = @Value(dischargeDiameter)
      TEST @Value(pipeDiameter) = @Value(inletDiameter)
    TEST_MODE = Automatic
    BOOL_OP = OR
    TEST_DESCRIPTION = ""
    FAILED -> AttributeCreator_5
AttributeCreator_5
    ATTR_TABLE = SET_TO Feature = @Value(fme_feature_type)
    -> oInterterminalPipeline_L (writer XLSXW_1)
oInterterminalPipeline_L (writer XLSXW_1)
    attributes: Feature auto(20), OBJECTID number(20), diameter auto(20), pipeDiameter auto(20)
utilitiesWater/wLineMain_L (reader FILEGDB_1)
    attributes: OBJECTID objectid, wLineMainIDPK text(20), sdsID guid, sdsFeatureName text(80), sdsFeatureDescription text(255), sdsMetadataID text(80), lengthSize double, lengthSizeUOM text(184), latitudeFrom double, latitudeTo double, longitudeFrom double, longitudeTo double, elevationFrom double, elevationTo double, elevationUOM text(184), CATCODE text(6), condRatingAssessDate text(8), condRatingMethod text(87), condRatingValue text(120), expectedServiceLife double, baseServiceLifeAdjustFactor text(76), calculatedServiceLife double, depthHeight double, depthHeightUOM text(184), facilityID text(10), flow double, functionalArea text(35), generalMaterialType text(8), specificMaterialType text(76), GEOLOC text(15),
      hasCathodicProtection text(77), hasLead text(77), installedDate text(8), inventoryControlNumber text(50), isWinterized text(77), lastPMDate text(8), lastRepairDate text(8), linearSegmentationGrouping text(100), maintainedBy text(76), MDI double, notes text(255), numberOfFailures smallint, operationalStatus text(76), pipeCoating text(76), pipeDiameter text(76), pipeDiameterUOM text(184), pipeInstallation text(76), pipeLining text(77), pipeSchedule text(30), PMtype text(76), projectID text(50), realPropertyNetworkIdentifier text(4), realPropertyUniqueIdentifier text(18), segmentID text(30), UCIAssessmentDate int, UDI double, uniformatIIComponent text(49), uniformatIISection text(61), uniformatIISystem text(39), utilityConditionIndex single,
      utilityNetworkType text(133), waterNetworkSubtype text(77), wMainLineType text(77), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255), Shape_Length double
    -> Tester_16
Tester_16
    TEST_CLAUSE:
      TEST @Value(operationalStatus) = removed
      TEST @Value(operationalStatus) = abandoned
    TEST_MODE = Automatic
    BOOL_OP = OR
    TEST_DESCRIPTION = ""
    FAILED -> Owner_22
Owner_22: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_2
AttributeKeeper_2
    KEEP_ATTRS = OBJECTID,fme_feature_type,pipeDiameter
    -> PointOnLineOverlayer [LINE]
utilitiesWater/wPumpStation_P (reader FILEGDB_1)
    attributes: OBJECTID objectid, wPumpStationIDPK text(20), sdsID guid, sdsFeatureName text(80), sdsFeatureDescription text(255), sdsMetadataID text(80), latitude double, longitude double, MGRS text(20), elevation double, elevationUOM text(184), annualAverageDailyFlow double, annualAverageDailyFlowUOM text(76), annualMaximumDailyFlow double, annualMaximumDailyFlowUOM text(76), CATCODE text(6), condRatingAssessDate text(8), condRatingMethod text(87), condRatingValue text(120), expectedServiceLife double, baseServiceLifeAdjustFactor text(76), calculatedServiceLife double, designCapacity double, designCapacityUOM text(187), envWtrQualPermitIDFK text(50), facilityID text(10), functionalArea text(35), GEOLOC text(15), hasCathodicProtection text(77), highWaterElevation text(20),
      installedDate text(8), inventoryControlNumber text(50), lastPMDate text(8), lastRepairDate text(8), linearSegmentationGrouping text(100), maintainedBy text(76), manufacturerName text(100), MDI double, notes text(255), numberOfFailures smallint, numberOfPumps smallint, operationalStatus text(76), permitCompliance text(77), permittedFlowRate double, permittedFlowRateUOM text(76), PMtype text(76), projectID text(50), realPropertyNetworkIdentifier text(4), realPropertyUniqueIdentifier text(18), SCADAControlID text(20), SCADAMonitorID text(20), segmentID text(30), UCIAssessmentDate int, UDI double, uniformatIIComponent text(49), uniformatIISection text(61), uniformatIISystem text(39), utilityConditionIndex single, utilityNetworkType text(133), wetWallCapacity double,
      installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_38
utilitiesWater/wMeter_P (reader FILEGDB_1)
    attributes: OBJECTID objectid, wMeterIDPK text(20), sdsID guid, sdsFeatureName text(80), sdsFeatureDescription text(255), sdsMetadataID text(80), latitude double, longitude double, MGRS text(20), elevation double, elevationUOM text(184), calibration text(8), CATCODE text(6), condRatingAssessDate text(8), condRatingMethod text(87), condRatingValue text(120), controlType text(76), expectedServiceLife double, baseServiceLifeAdjustFactor text(76), calculatedServiceLife double, depthHeight double, depthHeightUOM text(184), diameter text(76), diameterUOM text(184), enclosureCondition text(120), facilityID text(10), functionalArea text(35), GEOLOC text(15), hasCathodicProtection text(77), hasLead text(77),
      installedDate text(8), inventoryControlNumber text(50), isWinterized text(77), lastPMDate text(8), lastRepairDate text(8), linearSegmentationGrouping text(100), maintainedBy text(76), manufacturerName text(100), MDI double, meterID text(15), meterType text(255), model text(100), notes text(255), numberOfFailures smallint, operationalStatus text(76), PMtype text(76), projectID text(50), realPropertyNetworkIdentifier text(4), realPropertyUniqueIdentifier text(18), remoteRead text(77), remoteReadType text(76), segmentID text(30), UCIAssessmentDate int, UDI double, uniformatIIComponent text(49), uniformatIISection text(61), uniformatIISystem text(39), utilityConditionIndex single, utilityNetworkType text(133), waterNetworkSubtype text(77),
      installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_38
utilitiesWater/wControlValve_P (reader FILEGDB_1)
    attributes: OBJECTID objectid, wControlValveIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), controlValveType text(255), expectedServiceLife double, baseServiceLifeAdjustFactor text(76), calculatedServiceLife double, depthHeight double, depthHeightUOM text(184), diameter text(76), diameterUOM text(184), enclosureCondition text(120), facilityID text(10), functionalArea text(35), GEOLOC text(15), hasBypassValve text(77), hasCathodicProtection text(77),
      hasLead text(77), installedDate text(8), inventoryControlNumber text(50), isIsolation text(77), isMechanicalJoint text(77), isWinterized text(77), lastPMDate text(8), lastRepairDate text(8), linearSegmentationGrouping text(100), maintainedBy text(76), manufacturerName text(100), MDI double, model text(100), motorized text(77), notes text(255), numberOfFailures smallint, operationalStatus text(76), PMtype text(76), projectID text(50), realPropertyNetworkIdentifier text(4), realPropertyUniqueIdentifier text(18), regulationType text(77), segmentID text(30), UCIAssessmentDate int, UDI double, uniformatIIComponent text(49), uniformatIISection text(61), uniformatIISystem text(39), utilityConditionIndex single, utilityNetworkType text(133),
      waterNetworkSubtype text(77), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_38
utilitiesWater/wHydrant_P (reader FILEGDB_1)
    attributes: OBJECTID objectid, wHydrantIDPK text(18), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), expectedServiceLife double, baseServiceLifeAdjustFactor text(76), calculatedServiceLife double, depthHeight double, depthHeightUOM text(184), diameterUOM text(184), facilityID text(10), flow double, functionalArea text(35), GEOLOC text(15), hasCathodicProtection text(77), hasLead text(77), hydrantClearance text(77), inDiameter text(76),
      inOutFlowConnectionType text(65), inoutflowDiameter text(76), inoutflowDiameterUOM text(184), installedDate text(8), inventoryControlNumber text(50), isWinterized text(77), lastPMDate text(8), lastRepairDate text(8), linearSegmentationGrouping text(100), maintainedBy text(76), manufacturerName text(100), MDI double, model text(100), notes text(255), numberOfFailures smallint, operationalStatus text(76), operationNutConditionRating text(120), outDiameter double, PMtype text(76), projectID text(50), realPropertyNetworkIdentifier text(4), realPropertyUniqueIdentifier text(18), segmentID text(30), staticPressure double, UCIAssessmentDate int, UDI double, uniformatIIComponent text(49), uniformatIISection text(61), uniformatIISystem text(39), utilityConditionIndex single,
      utilityNetworkType text(133), waterHydrantType text(77), waterNetworkSubtype text(77), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_38
utilitiesWater/wFitting_P (reader FILEGDB_1)
    attributes: OBJECTID objectid, wFittingIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), expectedServiceLife double, baseServiceLifeAdjustFactor text(76), calculatedServiceLife double, depthHeight double, depthHeightUOM text(184), diameter text(76), diameterUOM text(184), facilityID text(10), fittingType text(76), functionalArea text(35), GEOLOC text(15), hasCathodicProtection text(77), hasLead text(77), installedDate text(8), inventoryControlNumber text(50),
      isWinterized text(77), lastPMDate text(8), lastRepairDate text(8), linearSegmentationGrouping text(100), maintainedBy text(76), manufacturerName text(100), MDI double, model text(100), notes text(255), numberOfFailures smallint, operationalStatus text(76), PMtype text(76), projectID text(50), realPropertyNetworkIdentifier text(4), realPropertyUniqueIdentifier text(18), segmentID text(30), UCIAssessmentDate int, UDI double, uniformatIIComponent text(49), uniformatIISection text(61), uniformatIISystem text(39), utilityConditionIndex single, utilityNetworkType text(133), waterNetworkSubtype text(77), installationID text(76), installationName text(76), siteID text(78), majorCommand text(76), realPropertySiteUniqueID text(80), wacInnrCode text(10),
      dataSteward text(20), country text(76), owner text(76), createDate date, creator text(30), dataCollection text(255), dataSource text(100), editor text(20), dateEdited date, metaNotes text(255), mediaLink text(255), narrative text(255)
    -> Tester_38
utilitiesWater/wPump_P (reader FILEGDB_1)
    attributes: OBJECTID objectid, wPumpIDPK text(20), sdsID guid, sdsFeatureName text(80), sdsFeatureDescription text(255), sdsMetadataID text(80), latitude double, longitude double, MGRS text(20), elevation double, elevationUOM text(184), averageDailyRunTime smallint, CATCODE text(6), condRatingAssessDate text(8), condRatingMethod text(87), condRatingValue text(120), controlType text(76), expectedServiceLife double, baseServiceLifeAdjustFactor text(76), calculatedServiceLife double, depthHeight double, depthHeightUOM text(184), diameterUOM text(184), electricalConditionRating text(120), facilityID text(10), functionalArea text(35), GEOLOC text(15), hasCathodicProtection text(77), hasLead text(77), inDiameter text(76),
      installedDate text(8), inventoryControlNumber text(50), isWinterized text(77), lastPMDate text(8), lastRepairDate text(8), linearSegmentationGrouping text(100), maintainedBy text(76), manufacturerName text(100), MDI double, model text(100), notes text(255), numberOfFailures smallint, operationalStatus text(76), outDiameter text(76), PMtype text(76), projectID text(50), pumpDesignHead text(30), pumpDesignHeadUOM text(184), pumpType text(76), ratedFlow double, ratedFlowUOM text(76), realPropertyNetworkIdentifier text(4), realPropertyUniqueIdentifier text(18), SCADAControlID text(20), SCADAMonitorID text(20), scheduledMaintenance text(8), segmentID text(30), structuralConditionRating text(120), UCIAssessmentDate int, UDI double,
      uniformatIIComponent text(49), uniformatIISection text(61), uniformatIISystem text(39), utilityConditionIndex single, utilityNetworkType text(133), waterNetworkSubtype text(77), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_38
utilitiesWater/wFireHydrant_P (reader FILEGDB_1)
    attributes: OBJECTID objectid, wFireHydrantIDPK text(18), sdsID guid, sdsFeatureName text(80), sdsFeatureDescription text(255), sdsMetadataID text(80), latitude double, longitude double, MGRS text(20), elevation double, elevationUOM text(184), CATCODE text(6), condRatingAssessDate text(8), condRatingMethod text(87), condRatingValue text(120), connectionPoint text(77), expectedServiceLife double, baseServiceLifeAdjustFactor text(76), calculatedServiceLife double, depthHeight double, depthHeightUOM text(184), diameter text(76), diameterUOM text(184), facilityID text(10), flow double, functionalArea text(35), GEOLOC text(15), hasCathodicProtection text(77), hasLead text(77), hydrantClass text(26),
      hydrantClearance text(77), inOutFlowConnectionType1 text(65), inOutFlowConnectionType2 text(65), inOutflowDiameter1 text(76), inOutflowDiameter2 text(76), inoutflowDiameterUOM text(184), installedDate text(8), inventoryControlNumber text(50), isWinterized text(77), lastPMDate text(8), lastRepairDate text(8), linearSegmentationGrouping text(100), maintainedBy text(76), manufacturerName text(100), MDI double, model text(100), notes text(255), numberOfFailures smallint, operationalStatus text(76), operationNutConditionRating text(120), PMtype text(76), projectID text(50), realPropertyNetworkIdentifier text(4), realPropertyUniqueIdentifier text(18), segmentID text(30), staticPressure double, UCIAssessmentDate int, UDI double, uniformatIIComponent text(49), uniformatIISection text(61),
      uniformatIISystem text(39), utilityConditionIndex single, utilityNetworkType text(133), waterNetworkSubtype text(77), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_38
Tester_38
    TEST_CLAUSE:
      TEST @Value(operationalStatus) = removed
      TEST @Value(operationalStatus) = abandoned
    TEST_MODE = Automatic
    BOOL_OP = OR
    TEST_DESCRIPTION = ""
    FAILED -> Owner_23
Owner_23: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper
AttributeKeeper
    KEEP_ATTRS = inOutflowDiameter1,inOutflowDiameter2,OBJECTID,outDiameter,inoutflowDiameter,inDiameter,diameter,fme_feature_type
    -> PointOnLineOverlayer_2 [POINT]
    -> PointOnLineOverlayer [POINT]
PointOnLineOverlayer
    TOLERANCE = .00000001
    ATTR_ACCUM_MODE = Merge Incoming
    OV_ATTR = _overlaps
    ATTR_CONFLICT_RES = Use Original
    POINT -> Tester
Tester
    TEST_CLAUSE:
      TEST pipeDiameter ATTRIBUTE_VALUE_NULL ""
      TEST pipeDiameter ATTRIBUTE_IS_EMPTY ""
      TEST pipeDiameter ATTRIBUTE_IS_MISSING ""
      TEST @Value(pipeDiameter) = @Value(diameter)
      TEST @Value(pipeDiameter) = @Value(inDiameter)
      TEST @Value(pipeDiameter) = @Value(outDiameter)
    TEST_MODE = Automatic
    BOOL_OP = OR
    TEST_DESCRIPTION = ""
    FAILED -> AttributeCreator_8
AttributeCreator_8
    ATTR_TABLE = SET_TO Feature = @Value(fme_feature_type)
    -> wLineMain_L (writer XLSXW_1)
wLineMain_L (writer XLSXW_1)
    attributes: Feature auto(20), OBJECTID number(20), diameter auto(20), inDiameter auto(20), outDiameter auto(20), pipeDiameter auto(20)
utilitiesWater/wLineService_L (reader FILEGDB_1)
    attributes: OBJECTID objectid, wLineServiceIDPK text(20), sdsID guid, sdsFeatureName text(80), sdsFeatureDescription text(255), sdsMetadataID text(80), lengthSize double, lengthSizeUOM text(184), latitudeFrom double, latitudeTo double, longitudeFrom double, longitudeTo double, elevationFrom double, elevationTo double, elevationUOM text(184), CATCODE text(6), condRatingAssessDate text(8), condRatingMethod text(87), condRatingValue text(120), expectedServiceLife double, baseServiceLifeAdjustFactor text(76), calculatedServiceLife double, depthHeight double, depthHeightUOM text(184), envWtrQualPermitIDFK text(50), facilityID text(10), fireFlow double, functionalArea text(35), generalMaterialType text(8), specificMaterialType text(76),
      GEOLOC text(15), hasCathodicProtection text(77), hasLead text(77), installedDate text(8), inventoryControlNumber text(50), isWinterized text(77), lastPMDate text(8), lastRepairDate text(8), linearSegmentationGrouping text(100), maintainedBy text(76), MDI double, notes text(255), numberOfFailures smallint, operationalStatus text(76), permitCompliance text(77), pipeCoating text(76), pipeDiameter text(76), pipeDiameterUOM text(184), pipeInstallation text(76), pipeLining text(77), pipeSchedule text(30), PMtype text(76), projectID text(50), realPropertyNetworkIdentifier text(4), realPropertyUniqueIdentifier text(18), segmentID text(30), serviceLineType text(77), UCIAssessmentDate int, UDI double, uniformatIIComponent text(49),
      uniformatIISection text(61), uniformatIISystem text(39), utilityConditionIndex single, utilityNetworkType text(133), waterNetworkSubtype text(77), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255), Shape_Length double
    -> Tester_39
Tester_39
    TEST_CLAUSE:
      TEST @Value(operationalStatus) = removed
      TEST @Value(operationalStatus) = abandoned
    TEST_MODE = Automatic
    BOOL_OP = OR
    TEST_DESCRIPTION = ""
    FAILED -> Owner_24
Owner_24: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_3
AttributeKeeper_3
    KEEP_ATTRS = OBJECTID,pipeDiameter,fme_feature_type
    -> PointOnLineOverlayer_2 [LINE]
PointOnLineOverlayer_2
    TOLERANCE = .00000001
    ATTR_ACCUM_MODE = Merge Incoming
    OV_ATTR = _overlaps
    ATTR_CONFLICT_RES = Use Original
    POINT -> Tester_7
Tester_7
    TEST_CLAUSE:
      TEST pipeDiameter ATTRIBUTE_VALUE_NULL ""
      TEST pipeDiameter ATTRIBUTE_IS_EMPTY ""
      TEST pipeDiameter ATTRIBUTE_IS_MISSING ""
      TEST @Value(pipeDiameter) = @Value(diameter)
      TEST @Value(pipeDiameter) = @Value(inDiameter)
      TEST @Value(pipeDiameter) = @Value(outDiameter)
    TEST_MODE = Automatic
    BOOL_OP = OR
    TEST_DESCRIPTION = ""
    FAILED -> AttributeCreator_10
AttributeCreator_10
    ATTR_TABLE = SET_TO Feature = @Value(fme_feature_type)
    -> wLineService_L (writer XLSXW_1)
wLineService_L (writer XLSXW_1)
    attributes: Feature auto(20), OBJECTID number(20), diameter auto(20), inDiameter auto(20), outDiameter auto(20), pipeDiameter auto(20)
utilitiesStormwater/dCulvert_L (reader FILEGDB_1)
    attributes: OBJECTID objectid, dCulvertIDPK text(20), sdsID guid, sdsFeatureName text(80), sdsFeatureDescription text(255), sdsMetadataID text(80), lengthSize double, lengthSizeUOM text(184), latitudeFrom double, latitudeTo double, longitudeFrom double, longitudeTo double, elevationFrom double, elevationTo double, elevationUOM text(184), boxCulvertDimension text(6), boxCulvertDimensionUOM text(184), CATCODE text(6), condRatingAssessDate text(8), condRatingMethod text(87), condRatingValue text(120), expectedServiceLife double, baseServiceLifeAdjustFactor text(76), calculatedServiceLife double, culvertType text(255), envWtrQualPermitIDFK text(50), facilityID text(5), functionalArea text(35), generalMaterialType text(8), specificMaterialType text(76),
      GEOLOC text(15), hasCathodicProtection text(77), infiltration text(120), infiltrationSource text(76), installedDate text(8), inventoryControlNumber text(50), isGated text(77), isLined text(77), lastPMDate text(8), lastRepairDate text(8), linearSegmentationGrouping text(100), maintainedBy text(76), MDI double, notes text(255), numberOfFailures smallint, operationalStatus text(76), ovalArchDimension text(5), overalArchDimensionUOM text(184), permitCompliance text(77), pipeDiameter text(76), pipeDiameterUOM text(184), PMtype text(76), projectID text(50), realPropertyNetworkIdentifier text(4), realPropertyUniqueIdentifier text(18), segmentID text(30), UCIAssessmentDate int, UDI double, uniformatIIComponent text(49), uniformatIISection text(61),
      uniformatIISystem text(39), utilityConditionIndex single, utilityNetworkType text(133), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255), Shape_Length double
    -> Tester_40
Tester_40
    TEST_CLAUSE:
      TEST @Value(operationalStatus) = removed
      TEST @Value(operationalStatus) = abandoned
    TEST_MODE = Automatic
    BOOL_OP = OR
    TEST_DESCRIPTION = ""
    FAILED -> Owner_25
Owner_25: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_6
AttributeKeeper_6
    KEEP_ATTRS = OBJECTID,pipeDiameter,fme_feature_type
    -> PointOnLineOverlayer_3 [LINE]
utilitiesStormwater/dLineGravity_L (reader FILEGDB_1)
    attributes: OBJECTID objectid, dLineGravityIDPK text(20), sdsID guid, sdsFeatureName text(80), sdsFeatureDescription text(255), sdsMetadataID text(80), lengthSize double, lengthSizeUOM text(184), latitudeFrom double, latitudeTo double, longitudeFrom double, longitudeTo double, elevationFrom double, elevationTo double, elevationUOM text(184), boxCulvertDimension text(6), boxCulvertDimensionUOM text(184), CATCODE text(6), condRatingAssessDate text(8), condRatingMethod text(87), condRatingValue text(120), expectedServiceLife double, baseServiceLifeAdjustFactor text(76), calculatedServiceLife double, crossSectionShape text(76), depthHeight double, depthHeightUOM text(184), envWtrQualPermitIDFK text(50), facilityID text(5), functionalArea text(35),
      generalMaterialType text(8), specificMaterialType text(76), GEOLOC text(15), hasCathodicProtection text(77), infiltration text(120), infiltrationSource text(76), installedDate text(8), inventoryControlNumber text(50), invertDownstreamElevation double, invertElevationUOM text(184), invertUpstreamElevation double, isCoated text(77), isLined text(77), lastPMDate text(8), lastRepairDate text(8), linearSegmentationGrouping text(100), maintainedBy text(76), MDI double, model text(100), notes text(255), numberOfFailures smallint, operationalStatus text(76), ovalArchDimension text(5), overalArchDimensionUOM text(184), permitCompliance text(77), pipeDiameter text(76), pipeDiameterUOM text(184), pipeInstallation text(76), PMtype text(76), projectID text(50),
      realPropertyNetworkIdentifier text(4), realPropertyUniqueIdentifier text(18), segmentID text(30), serialNumber text(100), slope double, UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255),
      Shape_Length double
    -> Tester_42
Tester_42
    TEST_CLAUSE:
      TEST @Value(operationalStatus) = removed
      TEST @Value(operationalStatus) = abandoned
    TEST_MODE = Automatic
    BOOL_OP = OR
    TEST_DESCRIPTION = ""
    FAILED -> Owner_27
Owner_27: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_5
AttributeKeeper_5
    KEEP_ATTRS = OBJECTID,fme_feature_type,pipeDiameter
    -> PointOnLineOverlayer_4 [LINE]
utilitiesStormwater/dDischarge_P (reader FILEGDB_1)
    attributes: OBJECTID objectid, dDischargeIDPK text(20), sdsID guid, sdsFeatureName text(80), sdsFeatureDescription text(255), sdsMetadataID text(80), latitude double, longitude double, MGRS text(20), elevation double, elevationUOM text(184), averageDischarge double, averageDischargeUOM text(76), CATCODE text(6), condRatingAssessDate text(8), condRatingMethod text(87), condRatingValue text(120), diameter text(76), diameterUOM text(184), effluentDischarge text(76), envWtrQualPermitIDFK text(50), facilityID text(5), functionalArea text(35), GEOLOC text(15), installedDate text(8), inventoryControlNumber text(50), isSampled text(77), lastPMDate text(8), lastRepairDate text(8), linearSegmentationGrouping text(100),
      MDI double, notes text(255), operationalStatus text(76), peakDischarge double, peakDischargeUOM text(76), permitCompliance text(77), permitedFlowRate double, permittedFlowRateUOM text(76), PMtype text(76), projectID text(50), realPropertyNetworkIdentifier text(4), realPropertyUniqueIdentifier text(18), receivingWaterBody text(150), segmentID text(30), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76),
      createDate date, creator text(30), dataCollection text(255), dataSource text(100), editor text(20), dateEdited date, metaNotes text(255), mediaLink text(255), narrative text(255)
    -> Tester_41
utilitiesStormwater/dPump_P (reader FILEGDB_1)
    attributes: OBJECTID objectid, dPumpIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), expectedServiceLife double, baseServiceLifeAdjustFactor text(76), calculatedServiceLife double, depthHeight double, depthHeightUOM text(184), diameter text(76), diameterUOM text(184), envWtrQualPermitIDFK text(50), facilityID text(5), functionalArea text(35), GEOLOC text(15), hasCathodicProtection text(77), inDiameter text(76), infiltration text(120),
      infiltrationSource text(76), installedDate text(8), inventoryControlNumber text(50), lastPMDate text(8), lastRepairDate text(8), linearSegmentationGrouping text(100), maintainedBy text(76), manufacturerName text(100), MDI double, model text(50), notes text(255), numberOfFailures smallint, operationalStatus text(76), outDiameter text(76), permitCompliance text(77), PMtype text(76), projectID text(50), pumpType text(76), ratedFlow double, ratedFlowUOM text(76), realPropertyNetworkIdentifier text(4), realPropertyUniqueIdentifier text(18), SCADAControlID text(20), SCADAMonitorID text(20), segmentID text(30), totalDynamicHead text(25), UCIAssessmentDate int, UDI double, uniformatIIComponent text(49), uniformatIISection text(61),
      uniformatIISystem text(39), utilityConditionIndex single, utilityNetworkType text(133), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_41
utilitiesStormwater/dControlValve_P (reader FILEGDB_1)
    attributes: OBJECTID objectid, dControlValveIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), expectedServiceLife double, baseServiceLifeAdjustFactor text(76), calculatedServiceLife double, dControlValveType text(255), depthHeight double, depthHeightUOM text(184), diameter text(76), diameterUOM text(184), envWtrQualPermitIDFK text(50), facilityID text(5), functionalArea text(35), GEOLOC text(15), hasBypassValve text(77), hasCathodicProtection text(77),
      installedDate text(8), inventoryControlNumber text(50), lastPMDate text(8), lastRepairDate text(8), linearSegmentationGrouping text(100), maintainedBy text(76), manufacturerName text(100), MDI double, model text(50), notes text(255), numberOfFailures smallint, operationalStatus text(76), permitCompliance text(77), PMtype text(76), projectID text(50), realPropertyNetworkIdentifier text(4), realPropertyUniqueIdentifier text(18), segmentID text(30), UCIAssessmentDate int, UDI double, uniformatIIComponent text(49), uniformatIISection text(61), uniformatIISystem text(39), utilityConditionIndex single, utilityNetworkType text(133), installationID text(76), installationName text(76), siteID text(78), majorCommand text(76), realPropertySiteUniqueID text(80),
      wacInnrCode text(10), dataSteward text(20), country text(76), owner text(76), createDate date, creator text(30), dataCollection text(255), dataSource text(100), editor text(20), dateEdited date, metaNotes text(255), mediaLink text(255), narrative text(255)
    -> Tester_41
Tester_41
    TEST_CLAUSE:
      TEST @Value(operationalStatus) = removed
      TEST @Value(operationalStatus) = abandoned
    TEST_MODE = Automatic
    BOOL_OP = OR
    TEST_DESCRIPTION = ""
    FAILED -> Owner_26
Owner_26: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_4
AttributeKeeper_4
    KEEP_ATTRS = outDiameter,inDiameter,diameter,fme_feature_type
    -> PointOnLineOverlayer_4 [POINT]
    -> PointOnLineOverlayer_3 [POINT]
PointOnLineOverlayer_3
    TOLERANCE = .00000001
    ATTR_ACCUM_MODE = Merge Incoming
    OV_ATTR = _overlaps
    ATTR_CONFLICT_RES = Use Original
    POINT -> Tester_2
Tester_2
    TEST_CLAUSE:
      TEST pipeDiameter ATTRIBUTE_VALUE_NULL ""
      TEST pipeDiameter ATTRIBUTE_IS_EMPTY ""
      TEST pipeDiameter ATTRIBUTE_IS_MISSING ""
      TEST @Value(pipeDiameter) = @Value(diameter)
      TEST @Value(pipeDiameter) = @Value(inDiameter)
      TEST @Value(pipeDiameter) = @Value(outDiameter)
    TEST_MODE = Automatic
    BOOL_OP = OR
    TEST_DESCRIPTION = ""
    FAILED -> AttributeCreator_11
AttributeCreator_11
    ATTR_TABLE = SET_TO Feature = @Value(fme_feature_type)
    -> dCulvert_L (writer XLSXW_1)
dCulvert_L (writer XLSXW_1)
    attributes: Feature auto(20), OBJECTID number(20), diameter auto(20), inDiameter auto(20), outDiameter auto(20), pipeDiameter auto(20)
PointOnLineOverlayer_4
    TOLERANCE = .00000001
    ATTR_ACCUM_MODE = Merge Incoming
    OV_ATTR = _overlaps
    ATTR_CONFLICT_RES = Use Original
    POINT -> Tester_8
Tester_8
    TEST_CLAUSE:
      TEST pipeDiameter ATTRIBUTE_VALUE_NULL ""
      TEST pipeDiameter ATTRIBUTE_IS_EMPTY ""
      TEST pipeDiameter ATTRIBUTE_IS_MISSING ""
      TEST @Value(pipeDiameter) = @Value(diameter)
      TEST @Value(pipeDiameter) = @Value(inDiameter)
      TEST @Value(pipeDiameter) = @Value(outDiameter)
    TEST_MODE = Automatic
    BOOL_OP = OR
    TEST_DESCRIPTION = ""
    FAILED -> AttributeCreator_13
AttributeCreator_13
    ATTR_TABLE = SET_TO Feature = @Value(fme_feature_type)
    -> dLineGravity_L (writer XLSXW_1)
dLineGravity_L (writer XLSXW_1)
    attributes: Feature auto(20), OBJECTID number(20), diameter auto(20), inDiameter auto(20), outDiameter auto(20), pipeDiameter auto(20)
utilitiesSewer/sLineGravityMain_L (reader FILEGDB_1)
    attributes: OBJECTID objectid, sLineGravityMainIDPK text(20), sdsID guid, sdsFeatureName text(80), sdsFeatureDescription text(255), sdsMetadataID text(80), lengthSize double, lengthSizeUOM text(184), latitudeFrom double, latitudeTo double, longitudeFrom double, longitudeTo double, elevationFrom double, elevationTo double, elevationUOM text(184), CATCODE text(6), condRatingAssessDate text(8), condRatingMethod text(87), condRatingValue text(120), expectedServiceLife double, baseServiceLifeAdjustFactor text(76), calculatedServiceLife double, crossSectionShape text(76), depthHeight double, depthHeightUOM text(184), envWtrQualPermitIDFK text(50), facilityID text(5), functionalArea text(35), generalMaterialType text(8), specificMaterialType text(76),
      GEOLOC text(15), hasCathodicProtection text(77), infiltration text(120), infiltrationSource text(76), installedDate text(8), inventoryControlNumber text(50), invertDownstreamElevation double, invertElevationUOM text(184), invertUpstreamElevation double, isCoated text(77), isLined text(77), isWinterized text(77), lastPMDate text(8), lastRepairDate text(8), linearSegmentationGrouping text(100), lineCapacity double, lineCapacityUOM text(76), maintainedBy text(76), MDI double, notes text(255), numberOfFailures smallint, operationalStatus text(76), permitCompliance text(77), pipeDiameter text(76), pipeDiameterUOM text(184), pipeInstallation text(76), PMtype text(76), projectID text(50), realPropertyNetworkIdentifier text(4), realPropertyUniqueIdentifier text(18),
      segmentID text(30), slope double, slopeUOM text(255), UCIAssessmentDate int, UDI double, uniformatIIComponent text(49), uniformatIISection text(61), uniformatIISystem text(39), utilityConditionIndex single, utilityNetworkType text(133), wasteWaterType text(76), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255), Shape_Length double
    -> Tester_43
Tester_43
    TEST_CLAUSE:
      TEST @Value(operationalStatus) = removed
      TEST @Value(operationalStatus) = abandoned
    TEST_MODE = Automatic
    BOOL_OP = OR
    TEST_DESCRIPTION = ""
    FAILED -> Owner_28
Owner_28: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_9
AttributeKeeper_9
    KEEP_ATTRS = OBJECTID,pipeDiameter,fme_feature_type
    -> PointOnLineOverlayer_5 [LINE]
utilitiesSewer/sLineGravityService_L (reader FILEGDB_1)
    attributes: OBJECTID objectid, sLineGravityServiceIDPK text(20), sdsID guid, sdsFeatureName text(80), sdsFeatureDescription text(255), sdsMetadataID text(80), lengthSize double, lengthSizeUOM text(184), latitudeFrom double, latitudeTo double, longitudeFrom double, longitudeTo double, elevationFrom double, elevationTo double, elevationUOM text(184), CATCODE text(6), condRatingAssessDate text(8), condRatingMethod text(87), condRatingValue text(120), expectedServiceLife double, baseServiceLifeAdjustFactor text(76), calculatedServiceLife double, crossSectionShape text(76), depthHeight double, depthHeightUOM text(184), envWtrQualPermitIDFK text(50), facilityID text(5), functionalArea text(35), generalMaterialType text(8), specificMaterialType text(76),
      GEOLOC text(15), hasCathodicProtection text(77), infiltration text(120), infiltrationSource text(76), installedDate text(8), inventoryControlNumber text(50), invertDownstreamElevation double, invertElevationUOM text(184), invertUpstreamElevation double, isCoated text(77), isLined text(77), isWinterized text(77), lastPMDate text(8), lastRepairDate text(8), linearSegmentationGrouping text(100), lineCapacity double, lineCapacityUOM text(76), maintainedBy text(76), MDI double, notes text(255), numberOfFailures smallint, operationalStatus text(76), permitCompliance text(77), pipeDiameter text(76), pipeDiameterUOM text(184), pipeInstallation text(76), PMtype text(76), projectID text(50), realPropertyNetworkIdentifier text(4), realPropertyUniqueIdentifier text(18),
      segmentID text(30), slope double, slopeUOM text(255), UCIAssessmentDate int, UDI double, uniformatIIComponent text(49), uniformatIISection text(61), uniformatIISystem text(39), utilityConditionIndex single, utilityNetworkType text(133), wasteWaterType text(76), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255), Shape_Length double
    -> Tester_44
Tester_44
    TEST_CLAUSE:
      TEST @Value(operationalStatus) = removed
      TEST @Value(operationalStatus) = abandoned
    TEST_MODE = Automatic
    BOOL_OP = OR
    TEST_DESCRIPTION = ""
    FAILED -> Owner_29
Owner_29: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_8
AttributeKeeper_8
    KEEP_ATTRS = OBJECTID,fme_feature_type,pipeDiameter
    -> PointOnLineOverlayer_6 [LINE]
utilitiesSewer/sLinePressurizedMain_L (reader FILEGDB_1)
    attributes: OBJECTID objectid, sLinePressurizedMainIDPK text(20), sdsID guid, sdsFeatureName text(80), sdsFeatureDescription text(255), sdsMetadataID text(80), lengthSize double, lengthSizeUOM text(184), latitudeFrom double, latitudeTo double, longitudeFrom double, longitudeTo double, elevationFrom double, elevationTo double, elevationUOM text(184), CATCODE text(6), condRatingAssessDate text(8), condRatingMethod text(87), condRatingValue text(120), expectedServiceLife double, baseServiceLifeAdjustFactor text(76), calculatedServiceLife double, depthHeight double, depthHeightUOM text(184), envWtrQualPermitIDFK text(50), facilityID text(5), functionalArea text(35), generalMaterialType text(8), specificMaterialType text(76), GEOLOC text(15),
      hasCathodicProtection text(77), installedDate text(8), inventoryControlNumber text(50), isLined text(77), isWinterized text(77), lastPMDate text(8), lastRepairDate text(8), linearSegmentationGrouping text(100), lineCapacity double, lineCapacityUOM text(76), linePressurizedType text(76), maintainedBy text(76), MDI double, notes text(255), numberOfFailures smallint, operationalStatus text(76), permitCompliance text(77), pipeDiameter text(76), pipeDiameterUOM text(184), pipeInstallation text(76), PMtype text(76), pressureRating double, pressureRatingUOM text(136), projectID text(50), realPropertyNetworkIdentifier text(4), realPropertyUniqueIdentifier text(18), segmentID text(30), UCIAssessmentDate int, UDI double, uniformatIIComponent text(49),
      uniformatIISection text(61), uniformatIISystem text(39), utilityConditionIndex single, utilityNetworkType text(133), wasteWaterType text(76), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255), Shape_Length double
    -> Tester_45
Tester_45
    TEST_CLAUSE:
      TEST @Value(operationalStatus) = removed
      TEST @Value(operationalStatus) = abandoned
    TEST_MODE = Automatic
    BOOL_OP = OR
    TEST_DESCRIPTION = ""
    FAILED -> Owner_30
Owner_30: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_11
AttributeKeeper_11
    KEEP_ATTRS = OBJECTID,pipeDiameter,fme_feature_type
    -> PointOnLineOverlayer_7 [LINE]
utilitiesSewer/sLinePressurizedService_L (reader FILEGDB_1)
    attributes: OBJECTID objectid, sLinePressurizedServiceIDPK text(20), sdsID guid, sdsFeatureName text(80), sdsFeatureDescription text(255), sdsMetadataID text(80), lengthSize double, lengthSizeUOM text(184), latitudeFrom double, latitudeTo double, longitudeFrom double, longitudeTo double, elevationFrom double, elevationTo double, elevationUOM text(184), CATCODE text(6), condRatingAssessDate text(8), condRatingMethod text(87), condRatingValue text(120), expectedServiceLife double, baseServiceLifeAdjustFactor text(76), calculatedServiceLife double, depthHeight double, depthHeightUOM text(184), envWtrQualPermitIDFK text(50), facilityID text(5), functionalArea text(35), generalMaterialType text(8), specificMaterialType text(76), GEOLOC text(15),
      hasCathodicProtection text(77), installedDate text(8), inventoryControlNumber text(50), isLined text(77), isWinterized text(77), lastPMDate text(8), lastRepairDate text(8), linearSegmentationGrouping text(100), lineCapacity double, lineCapacityUOM text(76), linePressurizedType text(76), maintainedBy text(76), MDI double, notes text(255), numberOfFailures smallint, operationalStatus text(76), permitCompliance text(77), pipeDiameter text(76), pipeDiameterUOM text(184), pipeInstallation text(76), PMtype text(76), pressureRating double, pressureRatingUOM text(136), projectID text(50), realPropertyNetworkIdentifier text(4), realPropertyUniqueIdentifier text(18), segmentID text(30), UCIAssessmentDate int, UDI double, uniformatIIComponent text(49),
      uniformatIISection text(61), uniformatIISystem text(39), utilityConditionIndex single, utilityNetworkType text(133), wasteWaterType text(76), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255), Shape_Length double
    -> Tester_46
Tester_46
    TEST_CLAUSE:
      TEST @Value(operationalStatus) = removed
      TEST @Value(operationalStatus) = abandoned
    TEST_MODE = Automatic
    BOOL_OP = OR
    TEST_DESCRIPTION = ""
    FAILED -> Owner_31
Owner_31: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_10
AttributeKeeper_10
    KEEP_ATTRS = OBJECTID,fme_feature_type,pipeDiameter
    -> PointOnLineOverlayer_8 [LINE]
utilitiesSewer/sCleanOut_P (reader FILEGDB_1)
    attributes: OBJECTID objectid, sCleanOutDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), expectedServiceLife double, baseServiceLifeAdjustFactor text(76), calculatedServiceLife double, diameter text(76), diameterUOM text(184), envWtrQualPermitIDFK text(50), facilityID text(5), functionalArea text(35), GEOLOC text(15), hasCathodicProtection text(77), installedDate text(8), inventoryControlNumber text(50), lastPMDate text(8), lastRepairDate text(8), linearSegmentationGrouping text(100),
      maintainedBy text(76), MDI double, notes text(255), numberOfFailures smallint, operationalStatus text(76), permitCompliance text(77), PMtype text(76), projectID text(50), realPropertyNetworkIdentifier text(4), realPropertyUniqueIdentifier text(18), segmentID text(30), UCIAssessmentDate int, UDI double, uniformatIIComponent text(49), uniformatIISection text(61), uniformatIISystem text(39), utilityConditionIndex single, utilityNetworkType text(133), wasteWaterType text(76), installationID text(76), installationName text(76), siteID text(78), majorCommand text(76), realPropertySiteUniqueID text(80), wacInnrCode text(10), dataSteward text(20), country text(76), owner text(76), createDate date, creator text(30),
      dataCollection text(255), dataSource text(100), editor text(20), dateEdited date, metaNotes text(255), mediaLink text(255), narrative text(255)
    -> Tester_47
utilitiesSewer/sPumpStation_P (reader FILEGDB_1)
    attributes: OBJECTID objectid, sPumpStationIDPK text(20), sdsID guid, sdsFeatureName text(80), sdsFeatureDescription text(255), sdsMetadataID text(80), latitude double, longitude double, MGRS text(20), elevation double, elevationUOM text(184), annualAverageDailyFlow double, annualAverageDailyFlowUOM text(76), annualMaximumDailyFlow double, annualMaximumDailyFlowUOM text(76), CATCODE text(6), condRatingAssessDate text(8), condRatingMethod text(87), condRatingValue text(120), expectedServiceLife double, baseServiceLifeAdjustFactor text(76), calculatedServiceLife double, designCapacity double, designCapacityUOM text(187), envWtrQualPermitIDFK text(50), facilityID text(10), functionalArea text(35), GEOLOC text(15), hasCathodicProtection text(77), highWaterElevation text(20),
      installedDate text(8), inventoryControlNumber text(50), lastPMDate text(8), lastRepairDate text(8), linearSegmentationGrouping text(100), maintainedBy text(76), manufacturerName text(100), MDI double, notes text(255), numberOfFailures smallint, numberOfPumps smallint, operationalStatus text(76), permitCompliance text(77), permittedFlowRate double, permittedFlowRateUOM text(76), PMtype text(76), projectID text(50), realPropertyNetworkIdentifier text(4), realPropertyUniqueIdentifier text(18), SCADAControlID text(20), SCADAMonitorID text(20), segmentID text(30), UCIAssessmentDate int, UDI double, uniformatIIComponent text(49), uniformatIISection text(61), uniformatIISystem text(39), utilityConditionIndex single, utilityNetworkType text(133), wetWallCapacity double,
      installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_47
utilitiesSewer/sFitting_P (reader FILEGDB_1)
    attributes: OBJECTID objectid, sFittingIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), expectedServiceLife double, baseServiceLifeAdjustFactor text(76), calculatedServiceLife double, depthHeight double, depthHeightUOM text(184), diameter text(76), diameterUOM text(184), envWtrQualPermitIDFK text(50), facilityID text(5), fittingConnectionType text(76), fittingType text(76), functionalArea text(35), GEOLOC text(15), hasCathodicProtection text(77), installedDate text(8),
      inventoryControlNumber text(50), lastPMDate text(8), lastRepairDate text(8), linearSegmentationGrouping text(100), maintainedBy text(76), MDI double, notes text(255), numberOfFailures smallint, operationalStatus text(76), permitCompliance text(77), PMtype text(76), projectID text(50), realPropertyNetworkIdentifier text(4), realPropertyUniqueIdentifier text(18), segmentID text(30), UCIAssessmentDate int, UDI double, uniformatIIComponent text(49), uniformatIISection text(61), uniformatIISystem text(39), utilityConditionIndex single, utilityNetworkType text(133), wasteWaterType text(76), installationID text(76), installationName text(76), siteID text(78), majorCommand text(76), realPropertySiteUniqueID text(80), wacInnrCode text(10), dataSteward text(20),
      country text(76), owner text(76), createDate date, creator text(30), dataCollection text(255), dataSource text(100), editor text(20), dateEdited date, metaNotes text(255), mediaLink text(255), narrative text(255)
    -> Tester_47
utilitiesSewer/sGreaseTrap_P (reader FILEGDB_1)
    attributes: OBJECTID objectid, sGreaseTrapIDPK text(20), sdsID guid, sdsFeatureName text(80), sdsFeatureDescription text(255), sdsMetadataID text(80), latitude double, longitude double, MGRS text(20), elevation double, elevationUOM text(184), capacity double, capacityUOM text(187), CATCODE text(6), condRatingAssessDate text(8), condRatingMethod text(87), condRatingValue text(120), expectedServiceLife double, baseServiceLifeAdjustFactor text(76), calculatedServiceLife double, depthHeight double, depthHeightUOM text(184), envWtrQualPermitIDFK text(50), facilityID text(5), functionalArea text(35), GEOLOC text(15), hasCathodicProtection text(77), hasGritChamber text(77), infiltration text(120), installedDate text(8),
      inventoryControlNumber text(50), lastPMDate text(8), lastRepairDate text(8), linearSegmentationGrouping text(100), maintainedBy text(76), manufacturerName text(100), MDI double, model text(50), notes text(255), numberOfFailures smallint, operationalStatus text(76), permitCompliance text(77), pipeCount smallint, PMtype text(76), projectID text(50), ratedFlow double, ratedFlowUOM text(76), realPropertyNetworkIdentifier text(4), realPropertyUniqueIdentifier text(18), segmentID text(30), structureType text(76), UCIAssessmentDate int, UDI double, uniformatIIComponent text(49), uniformatIISection text(61), uniformatIISystem text(39), utilityConditionIndex single, utilityNetworkType text(133), volume double, volumeUOM text(187),
      wasteWaterType text(76), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_47
utilitiesSewer/sPump_P (reader FILEGDB_1)
    attributes: OBJECTID objectid, sPumpIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), expectedServiceLife double, baseServiceLifeAdjustFactor text(76), calculatedServiceLife double, depthHeight double, depthHeightUOM text(184), dischargeDiameter text(76), dischargeDiameterUOM text(184), envWtrQualPermitIDFK text(50), facilityID text(5), functionalArea text(35), GEOLOC text(15), hasCathodicProtection text(77), inletDiameter text(76), inletDiameterUOM text(184),
      installedDate text(8), inventoryControlNumber text(50), lastPMDate text(8), lastRepairDate text(8), linearSegmentationGrouping text(100), maintainedBy text(76), manufacturerName text(100), MDI double, model text(50), notes text(255), numberOfFailures smallint, operationalStatus text(76), permitCompliance text(77), pipeCount smallint, PMtype text(76), pressureRating double, pressureRatingUOM text(136), projectID text(50), pumpType text(76), ratedFlow double, ratedFlowUOM text(76), realPropertyNetworkIdentifier text(4), realPropertyUniqueIdentifier text(18), SCADAControlID text(20), SCADAMonitorID text(20), segmentID text(30), totalDynamicHead double, totalDynamicHeadUOM text(184), UCIAssessmentDate int, UDI double,
      uniformatIIComponent text(49), uniformatIISection text(61), uniformatIISystem text(39), utilityConditionIndex single, utilityNetworkType text(133), wasteWaterType text(76), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_47
utilitiesSewer/sControlValve_P (reader FILEGDB_1)
    attributes: OBJECTID objectid, sControlValveIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), expectedServiceLife double, baseServiceLifeAdjustFactor text(76), calculatedServiceLife double, depthHeight double, depthHeightUOM text(184), diameter text(76), diameterUOM text(184), envWtrQualPermitIDFK text(50), facilityID text(5), functionalArea text(35), GEOLOC text(15), hasBypassValve text(77), hasCathodicProtection text(77), installedDate text(8),
      inventoryControlNumber text(50), lastPMDate text(8), lastRepairDate text(8), linearSegmentationGrouping text(100), maintainedBy text(76), manufacturerName text(100), MDI double, model text(50), notes text(255), numberOfFailures smallint, operationalStatus text(76), permitCompliance text(77), pipeCount smallint, PMtype text(76), projectID text(50), realPropertyNetworkIdentifier text(4), realPropertyUniqueIdentifier text(18), sControlValveType text(255), segmentID text(30), UCIAssessmentDate int, UDI double, uniformatIIComponent text(49), uniformatIISection text(61), uniformatIISystem text(39), utilityConditionIndex single, utilityNetworkType text(133), wasteWaterType text(76), installationID text(76), installationName text(76), siteID text(78),
      majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_47
utilitiesSewer/sOutfall_P (reader FILEGDB_1)
    attributes: OBJECTID objectid, sOutfallIDPK text(20), sdsID guid, sdsFeatureName text(80), sdsFeatureDescription text(255), sdsMetadataID text(80), latitude double, longitude double, MGRS text(20), elevation double, elevationUOM text(184), CATCODE text(6), diameter text(76), diameterUOM text(184), envWtrQualPermitIDFK text(50), facilityID text(5), functionalArea text(35), GEOLOC text(15), hasCathodicProtection text(77), inventoryControlNumber text(50), linearSegmentationGrouping text(100), maxPermitedFlowRate double, maxPermittedFlowRateUOM text(76), notes text(255), permitCompliance text(77), realPropertyNetworkIdentifier text(4), realPropertyUniqueIdentifier text(18), uniformatIIComponent text(49), uniformatIISection text(61), uniformatIISystem text(39),
      utilityNetworkType text(133), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_47
utilitiesSewer/sMeter_P (reader FILEGDB_1)
    attributes: OBJECTID objectid, sMeterIDPK text(20), sdsID guid, sdsFeatureName text(80), sdsFeatureDescription text(255), sdsMetadataID text(80), latitude double, longitude double, MGRS text(20), elevation double, elevationUOM text(184), calibration text(8), CATCODE text(6), condRatingAssessDate text(8), condRatingMethod text(87), condRatingValue text(120), controlType text(76), expectedServiceLife double, baseServiceLifeAdjustFactor text(76), calculatedServiceLife double, depthHeight double, depthHeightUOM text(184), envWtrQualPermitIDFK text(50), facilityID text(5), functionalArea text(35), GEOLOC text(15), hasCathodicProtection text(77), installedDate text(8), inventoryControlNumber text(50), lastPMDate text(8),
      lastRepairDate text(8), linearSegmentationGrouping text(100), maintainedBy text(76), manufacturerName text(100), MDI double, meterType text(255), model text(50), notes text(255), numberOfFailures smallint, operationalStatus text(76), permitCompliance text(77), pipeCount smallint, PMtype text(76), projectID text(50), ratedFlow double, ratedFlowUOM text(76), realPropertyNetworkIdentifier text(4), realPropertyUniqueIdentifier text(18), remoteRead text(77), remoteReadType text(76), segmentID text(30), UCIAssessmentDate int, UDI double, uniformatIIComponent text(49), uniformatIISection text(61), uniformatIISystem text(39), utilityConditionIndex single, utilityNetworkType text(133), wasteWaterType text(76), installationID text(76),
      installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_47
Tester_47
    TEST_CLAUSE:
      TEST @Value(operationalStatus) = removed
      TEST @Value(operationalStatus) = abandoned
    TEST_MODE = Automatic
    BOOL_OP = OR
    TEST_DESCRIPTION = ""
    FAILED -> Owner_32
Owner_32: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_7
AttributeKeeper_7
    KEEP_ATTRS = dischargeDiameter,diameter,fme_feature_type
    -> PointOnLineOverlayer_5 [POINT]
    -> PointOnLineOverlayer_6 [POINT]
    -> PointOnLineOverlayer_7 [POINT]
    -> PointOnLineOverlayer_8 [POINT]
PointOnLineOverlayer_5
    TOLERANCE = .00000001
    ATTR_ACCUM_MODE = Merge Incoming
    OV_ATTR = _overlaps
    ATTR_CONFLICT_RES = Use Original
    POINT -> Tester_9
Tester_9
    TEST_CLAUSE:
      TEST pipeDiameter ATTRIBUTE_VALUE_NULL ""
      TEST pipeDiameter ATTRIBUTE_IS_EMPTY ""
      TEST pipeDiameter ATTRIBUTE_IS_MISSING ""
      TEST @Value(pipeDiameter) = @Value(diameter)
      TEST @Value(pipeDiameter) = @Value(dischargeDiameter)
    TEST_MODE = Automatic
    BOOL_OP = OR
    TEST_DESCRIPTION = ""
    FAILED -> AttributeCreator_2
AttributeCreator_2
    ATTR_TABLE = SET_TO Feature = @Value(fme_feature_type)
    -> sLineGravityMain_L (writer XLSXW_1)
sLineGravityMain_L (writer XLSXW_1)
    attributes: Feature auto(20), OBJECTID number(20), diameter auto(20), pipeDiameter auto(20)
PointOnLineOverlayer_6
    TOLERANCE = .00000001
    ATTR_ACCUM_MODE = Merge Incoming
    OV_ATTR = _overlaps
    ATTR_CONFLICT_RES = Use Original
    POINT -> Tester_10
Tester_10
    TEST_CLAUSE:
      TEST pipeDiameter ATTRIBUTE_VALUE_NULL ""
      TEST pipeDiameter ATTRIBUTE_IS_EMPTY ""
      TEST pipeDiameter ATTRIBUTE_IS_MISSING ""
      TEST @Value(pipeDiameter) = @Value(diameter)
      TEST @Value(pipeDiameter) = @Value(dischargeDiameter)
    TEST_MODE = Automatic
    BOOL_OP = OR
    TEST_DESCRIPTION = ""
    FAILED -> AttributeCreator_7
AttributeCreator_7
    ATTR_TABLE = SET_TO Feature = @Value(fme_feature_type)
    -> sLineGravityService_L (writer XLSXW_1)
sLineGravityService_L (writer XLSXW_1)
    attributes: Feature auto(20), OBJECTID number(20), diameter auto(20), pipeDiameter auto(20)
PointOnLineOverlayer_7
    TOLERANCE = .00000001
    ATTR_ACCUM_MODE = Merge Incoming
    OV_ATTR = _overlaps
    ATTR_CONFLICT_RES = Use Original
    POINT -> Tester_11
Tester_11
    TEST_CLAUSE:
      TEST pipeDiameter ATTRIBUTE_VALUE_NULL ""
      TEST pipeDiameter ATTRIBUTE_IS_EMPTY ""
      TEST pipeDiameter ATTRIBUTE_IS_MISSING ""
      TEST @Value(pipeDiameter) = @Value(diameter)
      TEST @Value(pipeDiameter) = @Value(dischargeDiameter)
    TEST_MODE = Automatic
    BOOL_OP = OR
    TEST_DESCRIPTION = ""
    FAILED -> AttributeCreator_9
AttributeCreator_9
    ATTR_TABLE = SET_TO Feature = @Value(fme_feature_type)
    -> sLinePressurizedMain_L (writer XLSXW_1)
sLinePressurizedMain_L (writer XLSXW_1)
    attributes: Feature auto(20), OBJECTID number(20), diameter auto(20), pipeDiameter auto(20)
PointOnLineOverlayer_8
    TOLERANCE = .00000001
    ATTR_ACCUM_MODE = Merge Incoming
    OV_ATTR = _overlaps
    ATTR_CONFLICT_RES = Use Original
    POINT -> Tester_3
Tester_3
    TEST_CLAUSE:
      TEST pipeDiameter ATTRIBUTE_VALUE_NULL ""
      TEST pipeDiameter ATTRIBUTE_IS_EMPTY ""
      TEST pipeDiameter ATTRIBUTE_IS_MISSING ""
      TEST @Value(pipeDiameter) = @Value(diameter)
      TEST @Value(pipeDiameter) = @Value(dischargeDiameter)
    TEST_MODE = Automatic
    BOOL_OP = OR
    TEST_DESCRIPTION = ""
    FAILED -> AttributeCreator_3
AttributeCreator_3
    ATTR_TABLE = SET_TO Feature = @Value(fme_feature_type)
    -> sLinePressurizedService_L (writer XLSXW_1)
sLinePressurizedService_L (writer XLSXW_1)
    attributes: Feature auto(20), OBJECTID number(20), diameter auto(20), pipeDiameter auto(20)
utilitiesGas/gLineDistribution_L (reader FILEGDB_1)
    attributes: OBJECTID objectid, gLineDistributionIDPK text(20), sdsID guid, sdsFeatureName text(80), sdsFeatureDescription text(255), sdsMetadataID text(80), lengthSize double, lengthSizeUOM text(184), latitudeFrom double, latitudeTo double, longitudeFrom double, longitudeTo double, elevationFrom double, elevationTo double, elevationUOM text(184), CATCODE text(6), condRatingAssessDate text(8), condRatingMethod text(87), condRatingValue text(120), expectedServiceLife double, baseServiceLifeAdjustFactor text(76), calculatedServiceLife double, depthHeight double, depthHeightUOM text(184), envWtrQualPermitIDFK text(50), facilityID text(5), functionalArea text(35), gasType text(77), generalMaterialType text(8), specificMaterialType text(76),
      GEOLOC text(15), hasCathodicProtection text(77), installedDate text(8), inventoryControlNumber text(50), invertDownstreamElevation double, invertUpstreamElevation double, isCoated text(77), isLined text(77), lastPMDate text(8), lastRepairDate text(8), linearSegmentationGrouping text(100), maintainedBy text(76), MDI double, notes text(255), numberOfFailures smallint, operationalStatus text(76), permitCompliance text(77), pipeDiameter text(76), pipeDiameterUOM text(184), pipeInstallation text(76), pipeTestDate text(8), pipeType text(76), PMtype text(76), pressureRating double, pressureRatingUOM text(136), projectID text(50), ratedFlow double, ratedFlowUOM text(76), realPropertyNetworkIdentifier text(4), realPropertyUniqueIdentifier text(18),
      segmentID text(30), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255), Shape_Length double
    -> Tester_55
Tester_55
    TEST_CLAUSE:
      TEST @Value(operationalStatus) = removed
      TEST @Value(operationalStatus) = abandoned
    TEST_MODE = Automatic
    BOOL_OP = OR
    TEST_DESCRIPTION = ""
    FAILED -> Owner_40
Owner_40: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_21
AttributeKeeper_21
    KEEP_ATTRS = OBJECTID,pipeDiameter,fme_feature_type
    -> PointOnLineOverlayer_14 [LINE]
utilitiesGas/gLineService_L (reader FILEGDB_1)
    attributes: OBJECTID objectid, gLineServiceIDPK text(20), sdsID guid, sdsFeatureName text(80), sdsFeatureDescription text(255), sdsMetadataID text(80), lengthSize double, lengthSizeUOM text(184), latitudeFrom double, latitudeTo double, longitudeFrom double, longitudeTo double, elevationFrom double, elevationTo double, elevationUOM text(184), CATCODE text(6), condRatingAssessDate text(8), condRatingMethod text(87), condRatingValue text(120), expectedServiceLife double, baseServiceLifeAdjustFactor text(76), calculatedServiceLife double, depthHeight double, depthHeightUOM text(184), facilityID text(5), functionalArea text(35), gasType text(77), generalMaterialType text(8), specificMaterialType text(76), GEOLOC text(15),
      hasCathodicProtection text(77), installedDate text(8), inventoryControlNumber text(50), invertDownstreamElevation double, invertUpstreamElevation double, isCoated text(77), isLined text(77), lastLeakSurvey text(8), lastPMDate text(8), lastRepairDate text(8), linearSegmentationGrouping text(100), maintainedBy text(76), MDI double, notes text(255), numberOfFailures smallint, operationalStatus text(76), pipeDiameter text(76), pipeDiameterUOM text(184), pipeInstallation text(76), pipeTestDate text(8), pipeType text(76), PMtype text(76), pressureRating double, pressureRatingUOM text(136), projectID text(50), ratedFlow double, ratedFlowUOM text(76), realPropertyNetworkIdentifier text(4), realPropertyUniqueIdentifier text(18), segmentID text(30),
      UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255), Shape_Length double
    -> Tester_56
Tester_56
    TEST_CLAUSE:
      TEST @Value(operationalStatus) = removed
      TEST @Value(operationalStatus) = abandoned
    TEST_MODE = Automatic
    BOOL_OP = OR
    TEST_DESCRIPTION = ""
    FAILED -> Owner_41
Owner_41: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_20
AttributeKeeper_20
    KEEP_ATTRS = OBJECTID,fme_feature_type,pipeDiameter
    -> PointOnLineOverlayer_15 [LINE]
utilitiesGas/gPressureMonitoringDevice_P (reader FILEGDB_1)
    attributes: OBJECTID objectid, gPressureMonitoringDeviceIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), expectedServiceLife double, depthHeight double, depthHeightUOM text(184), facilityID text(10), functionalArea text(35), GEOLOC text(15), hasCathodicProtection text(77), installedDate text(8), inventoryControlNumber text(50), lastPMDate text(8), lastRepairDate text(8), linearSegmentationGrouping text(100), maintainedBy text(76), manufacturerName text(100),
      MDI double, model text(50), notes text(255), numberOfFailures smallint, operationalStatus text(76), PMtype text(76), pressureRating double, pressureRatingUOM text(136), projectID text(50), realPropertyNetworkIdentifier text(4), realPropertyUniqueIdentifier text(18), SCADA text(77), segmentID text(30), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date,
      creator text(30), dataCollection text(255), dataSource text(100), editor text(20), dateEdited date, metaNotes text(255), mediaLink text(255), narrative text(255)
    -> Tester_57
utilitiesGas/gOdorizer_P (reader FILEGDB_1)
    attributes: OBJECTID objectid, gOdorizerIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), expectedServiceLife double, baseServiceLifeAdjustFactor text(76), calculatedServiceLife double, depthHeight double, depthHeightUOM text(184), facilityID text(5), functionalArea text(35), GEOLOC text(15), hasCathodicProtection text(77), installedDate text(8), inventoryControlNumber text(50), lastPMDate text(8), lastRepairDate text(8), linearSegmentationGrouping text(100),
      maintainedBy text(76), manufacturerName text(100), MDI double, model text(50), notes text(255), numberOfFailures smallint, operationalStatus text(76), PMtype text(76), projectID text(50), realPropertyNetworkIdentifier text(4), realPropertyUniqueIdentifier text(18), segmentID text(30), storageCapacity text(76), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date,
      creator text(30), dataCollection text(255), dataSource text(100), editor text(20), dateEdited date, metaNotes text(255), mediaLink text(255), narrative text(255)
    -> Tester_57
utilitiesGas/gControlValve_P (reader FILEGDB_1)
    attributes: OBJECTID objectid, gControlValveIDPK text(20), sdsID guid, sdsFeatureName text(80), sdsFeatureDescription text(255), sdsMetadataID text(80), latitude double, longitude double, MGRS text(20), elevation double, elevationUOM text(184), capacityCFH double, CATCODE text(6), condRatingAssessDate text(8), condRatingMethod text(87), condRatingValue text(120), controlType text(76), expectedServiceLife double, baseServiceLifeAdjustFactor text(76), calculatedServiceLife double, depthHeight double, depthHeightUOM text(184), diameter text(76), diameterUOM text(184), facilityID text(5), functionalArea text(35), gControlValveType text(255), GEOLOC text(15), hasBypassValve text(77), hasCathodicProtection text(77),
      installedDate text(8), inventoryControlNumber text(50), isInsulated text(77), lastPMDate text(8), lastRepairDate text(8), linearSegmentationGrouping text(100), maintainedBy text(76), manufacturerName text(100), MDI double, model text(50), notes text(255), numberOfFailures smallint, operationalStatus text(76), pipeNumber smallint, PMtype text(76), pressureSetting double, pressureSettingUOM text(136), projectID text(50), realPropertyNetworkIdentifier text(4), realPropertyUniqueIdentifier text(18), reliefCapacityUOM text(76), segmentID text(30), UCIAssessmentDate int, UDI double, uniformatIIComponent text(49), uniformatIISection text(61), uniformatIISystem text(39), utilityConditionIndex single, utilityNetworkType text(133), installationID text(76),
      installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_57
utilitiesGas/gScrubber_P (reader FILEGDB_1)
    attributes: OBJECTID objectid, gScrubberIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), expectedServiceLife double, baseServiceLifeAdjustFactor text(76), calculatedServiceLife double, depthHeight double, depthHeightUOM text(184), diameter text(76), diameterUOM text(184), facilityID text(5), functionalArea text(35), GEOLOC text(15), hasCathodicProtection text(77), installedDate text(8), inventoryControlNumber text(50), lastPMDate text(8),
      lastRepairDate text(8), linearSegmentationGrouping text(100), maintainedBy text(76), manufacturerName text(100), MDI double, model text(50), notes text(255), numberOfFailures smallint, operationalStatus text(76), PMtype text(76), projectID text(50), realPropertyNetworkIdentifier text(4), realPropertyUniqueIdentifier text(18), segmentID text(30), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76),
      createDate date, creator text(30), dataCollection text(255), dataSource text(100), editor text(20), dateEdited date, metaNotes text(255), mediaLink text(255), narrative text(255)
    -> Tester_57
utilitiesGas/gPigLaunch_P (reader FILEGDB_1)
    attributes: OBJECTID objectid, gPigLaunchIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), expectedServiceLife double, baseServiceLifeAdjustFactor text(76), calculatedServiceLife double, depthHeight double, depthHeightUOM text(184), facilityID text(5), functionalArea text(35), GEOLOC text(15), hasCathodicProtection text(77), inServiceDate text(8), installedDate text(8), inventoryControlNumber text(50), lastPMDate text(8), lastRepairDate text(8), linearSegmentationGrouping text(100),
      maintainedBy text(76), manufacturerName text(100), MDI double, model text(50), notes text(255), numberOfFailures smallint, operationalStatus text(76), PMtype text(76), projectID text(50), realPropertyNetworkIdentifier text(4), realPropertyUniqueIdentifier text(18), segmentID text(30), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date, creator text(30),
      dataCollection text(255), dataSource text(100), editor text(20), dateEdited date, metaNotes text(255), mediaLink text(255), narrative text(255)
    -> Tester_57
utilitiesGas/gAlcoholInjectionEquipment_P (reader FILEGDB_1)
    attributes: OBJECTID objectid, gAlcoholInjectionEquipmentIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), expectedServiceLife double, baseServiceLifeAdjustFactor text(76), calculatedServiceLife double, depthHeight double, depthHeightUOM text(184), facilityID text(10), functionalArea text(35), GEOLOC text(15), hasCathodicProtection text(77), installedDate text(8), inventoryControlNumber text(50), lastPMDate text(8), lastRepairDate text(8), linearSegmentationGrouping text(100),
      maintainedBy text(76), manufacturerName text(100), MDI double, model text(50), notes text(255), numberOfFailures smallint, operationalStatus text(76), pipeCount smallint, PMtype text(76), projectID text(50), realPropertyNetworkIdentifier text(4), realPropertyUniqueIdentifier text(18), segmentID text(30), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date,
      creator text(30), dataCollection text(255), dataSource text(100), editor text(20), dateEdited date, metaNotes text(255), mediaLink text(255), narrative text(255)
    -> Tester_57
utilitiesGas/gStrainer_P (reader FILEGDB_1)
    attributes: OBJECTID objectid, gStrainerIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), expectedServiceLife double, baseServiceLifeAdjustFactor text(76), calculatedServiceLife double, depthHeight double, depthHeightUOM text(184), designPressureEntered double, designPressureStandard double, designPressureUOM text(136), diameter text(76), diameterUOM text(184), facilityID text(5), functionalArea text(35), GEOLOC text(15), hasCathodicProtection text(77),
      installedDate text(8), inventoryControlNumber text(50), lastPMDate text(8), lastRepairDate text(8), linearSegmentationGrouping text(100), maintainedBy text(76), manufacturerName text(100), maxDifferentialPressure double, MDI double, model text(50), notes text(255), numberOfFailures smallint, operationalStatus text(76), PMtype text(76), projectID text(50), realPropertyNetworkIdentifier text(4), realPropertyUniqueIdentifier text(18), segmentID text(30), UCIAssessmentDate int, UDI double, uniformatIIComponent text(49), uniformatIISection text(61), uniformatIISystem text(39), utilityConditionIndex single, utilityNetworkType text(133), installationID text(76), installationName text(76), siteID text(78), majorCommand text(76), realPropertySiteUniqueID text(80),
      wacInnrCode text(10), dataSteward text(20), country text(76), owner text(76), createDate date, creator text(30), dataCollection text(255), dataSource text(100), editor text(20), dateEdited date, metaNotes text(255), mediaLink text(255), narrative text(255)
    -> Tester_57
utilitiesGas/gLineHeater_P (reader FILEGDB_1)
    attributes: OBJECTID objectid, gLineHeaterIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), expectedServiceLife double, baseServiceLifeAdjustFactor text(76), calculatedServiceLife double, depthHeight double, depthHeightUOM text(184), facilityID text(5), functionalArea text(35), GEOLOC text(15), hasCathodicProtection text(77), installedDate text(8), inventoryControlNumber text(50), invertDownstreamElevation double, invertUpstreamElevation double, lastPMDate text(8), lastRepairDate text(8),
      linearSegmentationGrouping text(100), maintainedBy text(76), manufacturerName text(100), MDI double, model text(50), notes text(255), numberOfFailures smallint, operationalStatus text(76), PMtype text(76), projectID text(50), realPropertyNetworkIdentifier text(4), realPropertyUniqueIdentifier text(18), segmentID text(30), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date,
      creator text(30), dataCollection text(255), dataSource text(100), editor text(20), dateEdited date, metaNotes text(255), mediaLink text(255), narrative text(255)
    -> Tester_57
utilitiesGas/gGasLamp_P (reader FILEGDB_1)
    attributes: OBJECTID objectid, gGasLampIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), expectedServiceLife double, baseServiceLifeAdjustFactor text(76), calculatedServiceLife double, facilityID text(5), functionalArea text(35), gasUsage double, gasUsageRate text(76), GEOLOC text(15), hasCathodicProtection text(77), installedDate text(8), inventoryControlNumber text(50), lastPMDate text(8), lastRepairDate text(8), linearSegmentationGrouping text(100), maintainedBy text(76),
      manufacturerName text(100), MDI double, model text(50), notes text(255), numberOfFailures smallint, operationalStatus text(76), PMtype text(76), projectID text(50), realPropertyNetworkIdentifier text(4), realPropertyUniqueIdentifier text(18), segmentID text(30), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date, creator text(30), dataCollection text(255),
      dataSource text(100), editor text(20), dateEdited date, metaNotes text(255), mediaLink text(255), narrative text(255)
    -> Tester_57
utilitiesGas/gDrip_P (reader FILEGDB_1)
    attributes: OBJECTID objectid, gDripIDPK text(20), sdsID guid, sdsFeatureName text(80), sdsFeatureDescription text(255), sdsMetadataID text(80), latitude double, longitude double, MGRS text(20), elevation double, elevationUOM text(184), CATCODE text(6), condRatingAssessDate text(8), condRatingMethod text(87), condRatingValue text(120), controlType text(76), expectedServiceLife double, baseServiceLifeAdjustFactor text(76), calculatedServiceLife double, depthHeight double, depthHeightUOM text(184), facilityID text(5), functionalArea text(35), GEOLOC text(15), hasCathodicProtection text(77), installedDate text(8), inventoryControlNumber text(50), lastPMDate text(8), lastPumpedDate text(8), lastRepairDate text(8),
      linearSegmentationGrouping text(100), maintainedBy text(76), manufacturerName text(100), MDI double, model text(50), notes text(255), numberOfFailures smallint, operationalStatus text(76), PMtype text(76), projectID text(50), realPropertyNetworkIdentifier text(4), realPropertyUniqueIdentifier text(18), segmentID text(30), UCIAssessmentDate int, UDI double, uniformatIIComponent text(49), uniformatIISection text(61), uniformatIISystem text(39), utilityConditionIndex single, utilityNetworkType text(133), installationID text(76), installationName text(76), siteID text(78), majorCommand text(76), realPropertySiteUniqueID text(80), wacInnrCode text(10), dataSteward text(20), country text(76), owner text(76), createDate date,
      creator text(30), dataCollection text(255), dataSource text(100), editor text(20), dateEdited date, metaNotes text(255), mediaLink text(255), narrative text(255)
    -> Tester_57
utilitiesGas/gPumpStation_P (reader FILEGDB_1)
    attributes: OBJECTID objectid, gPumpStationIDPK text(20), sdsID guid, sdsFeatureName text(80), sdsFeatureDescription text(255), sdsMetadataID text(80), latitude double, longitude double, MGRS text(20), elevation double, elevationUOM text(184), annualAverageDailyFlow double, annualAverageDailyFlowUOM text(76), annualMaximumDailyFlow double, annualMaximumDailyFlowUOM text(76), CATCODE text(6), condRatingAssessDate text(8), condRatingMethod text(87), condRatingValue text(120), expectedServiceLife double, baseServiceLifeAdjustFactor text(76), calculatedServiceLife double, designCapacity double, designCapacityUOM text(187), envWtrQualPermitIDFK text(50), facilityID text(10), functionalArea text(35), GEOLOC text(15), hasCathodicProtection text(77), highWaterElevation text(20),
      installedDate text(8), inventoryControlNumber text(50), lastPMDate text(8), lastRepairDate text(8), linearSegmentationGrouping text(100), maintainedBy text(76), manufacturerName text(100), MDI double, notes text(255), numberOfFailures smallint, numberOfPumps smallint, operationalStatus text(76), permitCompliance text(77), permittedFlowRate double, permittedFlowRateUOM text(76), PMtype text(76), projectID text(50), realPropertyNetworkIdentifier text(4), realPropertyUniqueIdentifier text(18), SCADAControlID text(20), SCADAMonitorID text(20), segmentID text(30), UCIAssessmentDate int, UDI double, uniformatIIComponent text(49), uniformatIISection text(61), uniformatIISystem text(39), utilityConditionIndex single, utilityNetworkType text(133), wetWallCapacity double,
      installationID text(76), installationName text(76), siteID text(78), majorCommand text(76), realPropertySiteUniqueID text(80), wacInnrCode text(10), dataSteward text(20), country text(76), owner text(76), createDate date, creator text(30), dataCollection text(255), dataSource text(100), editor text(20), dateEdited date, metaNotes text(255), mediaLink text(255), narrative text(255)
    -> Tester_57
Tester_57
    TEST_CLAUSE:
      TEST @Value(operationalStatus) = removed
      TEST @Value(operationalStatus) = abandoned
    TEST_MODE = Automatic
    BOOL_OP = OR
    TEST_DESCRIPTION = ""
    FAILED -> Owner_42
Owner_42: Tester
    TEST_CLAUSE:
      STRING_TEST @Value(owner) = county
      STRING_TEST @Value(owner) = hostNation
      STRING_TEST @Value(owner) = NATO
      STRING_TEST @Value(owner) = private
      STRING_TEST @Value(owner) = state
      STRING_TEST @Value(owner) = USA
      STRING_TEST @Value(owner) = USCG
      STRING_TEST @Value(owner) = USMC
      STRING_TEST @Value(owner) = USN
      TEST @Value(owner) = federal
    TEST_MODE = Automatic
    BOOL_OP = OR
    TEST_DESCRIPTION = ""
    FAILED -> AttributeKeeper_19
AttributeKeeper_19
    KEEP_ATTRS = OBJECTID,orificeDiameter,diameter,fme_feature_type
    -> PointOnLineOverlayer_15 [POINT]
    -> PointOnLineOverlayer_14 [POINT]
PointOnLineOverlayer_14
    TOLERANCE = .00000001
    ATTR_ACCUM_MODE = Merge Incoming
    OV_ATTR = _overlaps
    ATTR_CONFLICT_RES = Use Original
    POINT -> Tester_15
Tester_15
    TEST_CLAUSE:
      TEST pipeDiameter ATTRIBUTE_VALUE_NULL ""
      TEST pipeDiameter ATTRIBUTE_IS_EMPTY ""
      TEST pipeDiameter ATTRIBUTE_IS_MISSING ""
      TEST @Value(pipeDiameter) = @Value(diameter)
    TEST_MODE = Automatic
    BOOL_OP = OR
    TEST_DESCRIPTION = ""
    FAILED -> AttributeCreator_16
AttributeCreator_16
    ATTR_TABLE = SET_TO Feature = @Value(fme_feature_type)
    -> gLineDistribution_L (writer XLSXW_1)
gLineDistribution_L (writer XLSXW_1)
    attributes: Feature auto(20), OBJECTID number(20), pipeDiameter auto(20), diameter auto(20)
PointOnLineOverlayer_15
    TOLERANCE = .00000001
    ATTR_ACCUM_MODE = Merge Incoming
    OV_ATTR = _overlaps
    ATTR_CONFLICT_RES = Use Original
    POINT -> Tester_6
Tester_6
    TEST_CLAUSE:
      TEST pipeDiameter ATTRIBUTE_VALUE_NULL ""
      TEST pipeDiameter ATTRIBUTE_IS_EMPTY ""
      TEST pipeDiameter ATTRIBUTE_IS_MISSING ""
      TEST @Value(pipeDiameter) = @Value(diameter)
    TEST_MODE = Automatic
    BOOL_OP = OR
    TEST_DESCRIPTION = ""
    FAILED -> AttributeCreator_6
AttributeCreator_6
    ATTR_TABLE = SET_TO Feature = @Value(fme_feature_type)
    -> gLineService_L (writer XLSXW_1)
gLineService_L (writer XLSXW_1)
    attributes: Feature auto(20), OBJECTID number(20), pipeDiameter auto(20), diameter auto(20)
